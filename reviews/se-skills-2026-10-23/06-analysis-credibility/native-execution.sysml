package BlueDogWingActuator {
    private import ScalarValues::*;
    public import MarineActuation::*;
    doc /* Output-shaft torque and speed drive electrical consumption. Efficiency
     * and idle/no-load losses are measured or bounded inputs, not free design
     * improvements. A self-locking candidate may be studied with holding motor
     * power zero, but that assumption is distinct from verified holding behavior.
     * The external search must retain power-loss trim and capsize checks. */

    analysis accountingExample {
        doc /* Arithmetic check, not component specifications or mission evidence.
         * 1 Nm at 0.2 rad/s; 80% motor, 40% gearbox; 1 W no-load,
         * 0.1 W controller; 2% moving, 98% holding. */
        out attribute locked : Real [3] ordered nonunique = DrivePower(1,0.2,0.8,0.4,1,0.1,0,0.02,0.98);
        out attribute poweredHold : Real [3] ordered nonunique = DrivePower(1,0.2,0.8,0.4,1,0.1,2,0.02,0.98);
        out attribute lockedWhPerDay : Real = DailyEnergy(locked#(1),24);
        out attribute poweredHoldWhPerDay : Real = DailyEnergy(poweredHold#(1),24);
    }
    dependency sustainedEnergy from DrivePower to BlueDogRequirements::sustainedEnergyFeasibility;
    dependency lockedTrimRecovery from DrivePower to BlueDogRequirements::capsizeControlRecovery;
    dependency loadSizing from MastTorque to BlueDogStructure::structuralIntegrity;
}

package BlueDogAerodynamicPolicy {
    private import ScalarValues::*;
    part sizing {
        doc /* Engineering assumptions for a restricted, attached-flow sizing case.
         * These are not measured confidence bounds or a demonstrated stall boundary.
         * Published crescent-wing tests establish method relevance, but their section,
         * Reynolds number and setup do not validate this CAD geometry. */
        attribute incidenceLowDeg : Real = -4;
        attribute incidenceHighDeg : Real = 8;
        attribute heelLimitDeg : Real = 20;
        attribute profileCd : Real = 0.04;
        attribute clLimit : Real = 0.9;
        attribute liftScale : Real = 0.7;
        attribute dragScale : Real = 1.4;
        attribute momentScale : Real = 1.4;
        metadata rationale : ModelingMetadata::Rationale { text = "Use the former adverse aerodynamic case for primary sizing. Restrict nominal incidence and heel to reduce reliance on separated flow and large spanwise inflow. The observed heel sensitivity motivates additional conservatism, not a universal calibrated correction. Moment uncertainty is independent of reduced lift credit so lower propulsion credit does not automatically reduce predicted actuator demand. All geometry variables remain free within their existing model brackets."; }
        metadata issue : ModelingMetadata::Issue { text = "Matched low-Re forward/reverse section measurements, measured pitching moments, finite-thickness effects, and heel-dependent full-grid validation remain missing. The retained cosine projection and uncertainty factors are provisional. A feasible solve establishes only feasibility under these assumptions."; }
    }
    part stress {
        attribute profileCd : Real = 0.06;
        attribute clLimit : Real = 0.8;
        attribute liftScale : Real = 0.55;
        attribute dragScale : Real = 1.6;
        metadata rationale : ModelingMetadata::Rationale { text = "An additional uncalibrated adverse hypothesis, not a probability distribution or a validated worst case. Re-solve controls at the selected geometry to expose remaining sensitivity."; }
    }
    analysis convergenceInputs {
        out attribute aspect : Real = 4;
        out attribute camber : Real = 1;
        out attribute meshes : Integer [3] ordered = (24,48,72);
        out attribute wakeIterations : Integer [3] ordered = (5,15,30);
        out attribute absoluteTolerance : Real [3] ordered = (0.03,0.01,0.02);
        doc /* Compare CL, induced CD and CMy over nominal incidence -4..8 degrees.
         * Crossed mesh/wake checks on both chord directions. Engineering numerical
         * screening tolerances only; passing does not establish physical validity. */
    }
    dependency supports from sizing to BlueDogRequirements::cruiseEvidence;
    dependency evidence from sizing to BlueDogWingHeel::sweepInputs;
    dependency literature from sizing to BlueDogSourceEvidence::sail4;
    dependency actuator from sizing to BlueDogRequirements::sustainedEnergyFeasibility;
}

package BlueDogAvoidanceFailures {
    private import ScalarValues::*; private import FailureAnalysis::*; private import CauseAndEffect::*;
    doc /* Qualitative, conditional avoidance failure analysis. All review actions remain open. Tree propositions are defined over one encounter response interval. Fallback unavailable means no complete timely safe fallback, not merely a stopped motor. Other users avoiding Blue Dog are not credited as a safeguard. No probability or exhaustive coverage claim. */
    occurrence def Exposure {
        occurrence encounterDemand : Event { attribute :>> description = "An encounter requires effective separation control within the available response time."; }
        occurrence missedDetection : Event { attribute :>> description = "A relevant target is not observed before the response deadline."; }
        occurrence lateObservation : Event { attribute :>> description = "Delivered target information is too old for a supported response."; }
        occurrence falseOrSwappedTrack : Event { attribute :>> description = "A false target or identity swap corrupts the encounter picture."; }
        occurrence wrongClassification : Event { attribute :>> description = "An incorrect target class, tack, status or occupant assessment is treated as reliable."; }
        occurrence wrongMotionPrediction : Event { attribute :>> description = "The credited target trajectory or swept extent excludes the actual encounter."; }
        occurrence wrongRuleAssessment : Event { attribute :>> description = "The controller applies the wrong duty, loses an overtaking duty or uses unsupported context."; }
        occurrence noFeasibleCommand : Event { attribute :>> description = "No timely safe, rule-consistent primary command is available."; }
        occurrence unsafeCourtesyChange : Event { attribute :>> description = "A discretionary courtesy change conflicts with an established encounter duty or another avoidance action."; }
        occurrence steeringUnavailable : Event { attribute :>> description = "The vessel cannot achieve the steering motion credited to the response."; }
        occurrence sailControlUnavailable : Event { attribute :>> description = "The vessel cannot achieve the sail-force change credited to the response."; }
        occurrence unobservedExecutionError : Event { attribute :>> description = "Actual motion diverges from the plan without timely corrective action."; }
        occurrence sharedPowerLoss : Event { attribute :>> description = "One shared power fault defeats the credited primary and recovery paths during the same demand."; }
        occurrence sharedComputeLoss : Event { attribute :>> description = "One shared compute, timebase or data-path fault defeats both credited response paths."; }
        occurrence unsafeAbortTransition : Event { attribute :>> description = "A command-arbitration, reset or propulsion-gating fault during transition defeats a timely safe fallback. A qualification-state error alone does not assert this event."; }
        occurrence inadequateRecoveryObservation : Event { attribute :>> description = "Recovery has no adequate independent observation and navigation capability for the encounter."; }
        occurrence noSafeRecoveryRoute : Event { attribute :>> description = "No accessible recovery route preserves separation and boundary safety."; }
        occurrence recoveryTooLate : Event { attribute :>> description = "The complete recovery response cannot act before the separation deadline."; }
        occurrence <'Observation unavailable'> OR_observationUnavailable : OrGate { attribute :>> description = "The primary observation picture is unusable for a safe response."; ref occurrence :>> inputs = (missedDetection, lateObservation, falseOrSwappedTrack); }
        connection OR_observationUnavailable_0 : Causation connect missedDetection to OR_observationUnavailable { metadata CausationMetadata { isNecessary = false; isSufficient = true; } }
        connection OR_observationUnavailable_1 : Causation connect lateObservation to OR_observationUnavailable { metadata CausationMetadata { isNecessary = false; isSufficient = true; } }
        connection OR_observationUnavailable_2 : Causation connect falseOrSwappedTrack to OR_observationUnavailable { metadata CausationMetadata { isNecessary = false; isSufficient = true; } }
        occurrence <'Assessment wrong'> OR_assessmentWrong : OrGate { attribute :>> description = "Primary encounter assessment is unsafe."; ref occurrence :>> inputs = (wrongClassification, wrongMotionPrediction, wrongRuleAssessment); }
        connection OR_assessmentWrong_0 : Causation connect wrongClassification to OR_assessmentWrong { metadata CausationMetadata { isNecessary = false; isSufficient = true; } }
        connection OR_assessmentWrong_1 : Causation connect wrongMotionPrediction to OR_assessmentWrong { metadata CausationMetadata { isNecessary = false; isSufficient = true; } }
        connection OR_assessmentWrong_2 : Causation connect wrongRuleAssessment to OR_assessmentWrong { metadata CausationMetadata { isNecessary = false; isSufficient = true; } }
        occurrence <'Command unsafe'> OR_commandUnsafe : OrGate { attribute :>> description = "Primary command selection cannot provide a safe response."; ref occurrence :>> inputs = (noFeasibleCommand, unsafeCourtesyChange); }
        connection OR_commandUnsafe_0 : Causation connect noFeasibleCommand to OR_commandUnsafe { metadata CausationMetadata { isNecessary = false; isSufficient = true; } }
        connection OR_commandUnsafe_1 : Causation connect unsafeCourtesyChange to OR_commandUnsafe { metadata CausationMetadata { isNecessary = false; isSufficient = true; } }
        occurrence <'Maneuver unavailable'> OR_maneuverUnavailable : OrGate { attribute :>> description = "Primary maneuver execution cannot provide a safe response."; ref occurrence :>> inputs = (steeringUnavailable, sailControlUnavailable, unobservedExecutionError); }
        connection OR_maneuverUnavailable_0 : Causation connect steeringUnavailable to OR_maneuverUnavailable { metadata CausationMetadata { isNecessary = false; isSufficient = true; } }
        connection OR_maneuverUnavailable_1 : Causation connect sailControlUnavailable to OR_maneuverUnavailable { metadata CausationMetadata { isNecessary = false; isSufficient = true; } }
        connection OR_maneuverUnavailable_2 : Causation connect unobservedExecutionError to OR_maneuverUnavailable { metadata CausationMetadata { isNecessary = false; isSufficient = true; } }
        occurrence <'Primary response unavailable'> OR_primaryUnavailable : OrGate { attribute :>> description = "No effective timely primary separation response remains."; ref occurrence :>> inputs = (OR_observationUnavailable, OR_assessmentWrong, OR_commandUnsafe, OR_maneuverUnavailable, sharedPowerLoss, sharedComputeLoss); }
        connection OR_primaryUnavailable_0 : Causation connect OR_observationUnavailable to OR_primaryUnavailable { metadata CausationMetadata { isNecessary = false; isSufficient = true; } }
        connection OR_primaryUnavailable_1 : Causation connect OR_assessmentWrong to OR_primaryUnavailable { metadata CausationMetadata { isNecessary = false; isSufficient = true; } }
        connection OR_primaryUnavailable_2 : Causation connect OR_commandUnsafe to OR_primaryUnavailable { metadata CausationMetadata { isNecessary = false; isSufficient = true; } }
        connection OR_primaryUnavailable_3 : Causation connect OR_maneuverUnavailable to OR_primaryUnavailable { metadata CausationMetadata { isNecessary = false; isSufficient = true; } }
        connection OR_primaryUnavailable_4 : Causation connect sharedPowerLoss to OR_primaryUnavailable { metadata CausationMetadata { isNecessary = false; isSufficient = true; } }
        connection OR_primaryUnavailable_5 : Causation connect sharedComputeLoss to OR_primaryUnavailable { metadata CausationMetadata { isNecessary = false; isSufficient = true; } }
        occurrence <'Recovery response unavailable'> OR_recoveryUnavailable : OrGate { attribute :>> description = "No effective timely fallback separation response remains."; ref occurrence :>> inputs = (unsafeAbortTransition, inadequateRecoveryObservation, noSafeRecoveryRoute, recoveryTooLate, sharedPowerLoss, sharedComputeLoss); }
        connection OR_recoveryUnavailable_0 : Causation connect unsafeAbortTransition to OR_recoveryUnavailable { metadata CausationMetadata { isNecessary = false; isSufficient = true; } }
        connection OR_recoveryUnavailable_1 : Causation connect inadequateRecoveryObservation to OR_recoveryUnavailable { metadata CausationMetadata { isNecessary = false; isSufficient = true; } }
        connection OR_recoveryUnavailable_2 : Causation connect noSafeRecoveryRoute to OR_recoveryUnavailable { metadata CausationMetadata { isNecessary = false; isSufficient = true; } }
        connection OR_recoveryUnavailable_3 : Causation connect recoveryTooLate to OR_recoveryUnavailable { metadata CausationMetadata { isNecessary = false; isSufficient = true; } }
        connection OR_recoveryUnavailable_4 : Causation connect sharedPowerLoss to OR_recoveryUnavailable { metadata CausationMetadata { isNecessary = false; isSufficient = true; } }
        connection OR_recoveryUnavailable_5 : Causation connect sharedComputeLoss to OR_recoveryUnavailable { metadata CausationMetadata { isNecessary = false; isSufficient = true; } }
        occurrence <'Safe separation unsupported'> AND_safeSeparationUnsupported : AndGate { attribute :>> description = "During an encounter demand, neither primary nor fallback provides a supported safe separation response. This is capability loss, not a predicted collision."; ref occurrence :>> inputs = (encounterDemand, OR_primaryUnavailable, OR_recoveryUnavailable); }
        connection AND_safeSeparationUnsupported_0 : Causation connect encounterDemand to AND_safeSeparationUnsupported { metadata CausationMetadata { isNecessary = true; isSufficient = false; } }
        connection AND_safeSeparationUnsupported_1 : Causation connect OR_primaryUnavailable to AND_safeSeparationUnsupported { metadata CausationMetadata { isNecessary = true; isSufficient = false; } }
        connection AND_safeSeparationUnsupported_2 : Causation connect OR_recoveryUnavailable to AND_safeSeparationUnsupported { metadata CausationMetadata { isNecessary = true; isSufficient = false; } }
    }
    occurrence exposure : Exposure;
    analysis def EvaluateExposure { subject scenario : Exposure; out attribute primaryUnavailable : Boolean = scenario.OR_primaryUnavailable.present; out attribute recoveryUnavailable : Boolean = scenario.OR_recoveryUnavailable.present; out attribute safeSeparationUnsupported : Boolean = scenario.AND_safeSeparationUnsupported.present; }
    occurrence fixedAngularGap : Event { attribute :>> description = "Rig masking or heel opens an unobserved sector through the response deadline."; }
    connection fixedAngularGapContributes : Causation connect fixedAngularGap to exposure.missedDetection { doc /* Conditional design hypothesis for SC-01 / SC-02; not an installed configuration or individually sufficient physical causal claim. */ }
    occurrence fixedStaleFrames : Event { attribute :>> description = "Dropped or frozen camera frames are presented as current tracks."; }
    connection fixedStaleFramesContributes : Causation connect fixedStaleFrames to exposure.lateObservation { doc /* Conditional design hypothesis for SC-01 / SC-02; not an installed configuration or individually sufficient physical causal claim. */ }
    occurrence wetOptics : Event { attribute :>> description = "Spray, condensation, glare or darkness defeats required optical observation."; }
    connection wetOpticsContributes : Causation connect wetOptics to exposure.missedDetection { doc /* Conditional design hypothesis for SC-01 / SC-02 / SC-03; not an installed configuration or individually sufficient physical causal claim. */ }
    occurrence sharedHub : Event { attribute :>> description = "A common USB hub or host loses all credited optical channels."; }
    connection sharedHubContributes : Causation connect sharedHub to exposure.missedDetection { doc /* Conditional design hypothesis for SC-01 / SC-02 / SC-03; not an installed configuration or individually sufficient physical causal claim. */ }
    occurrence scannerJam : Event { attribute :>> description = "Scanner stops or reports a false azimuth while targets remain outside its view."; }
    connection scannerJamContributes : Causation connect scannerJam to exposure.missedDetection { doc /* Conditional design hypothesis for SC-03; not an installed configuration or individually sufficient physical causal claim. */ }
    occurrence scannerRevisit : Event { attribute :>> description = "Sweep, cable-safe return or processing creates excessive sector revisit time."; }
    connection scannerRevisitContributes : Causation connect scannerRevisit to exposure.lateObservation { doc /* Conditional design hypothesis for SC-03; not an installed configuration or individually sufficient physical causal claim. */ }
    occurrence scannerCable : Event { attribute :>> description = "Cable winding, seal friction or ingress prevents the required scan."; }
    connection scannerCableContributes : Causation connect scannerCable to exposure.missedDetection { doc /* Conditional design hypothesis for SC-03; not an installed configuration or individually sufficient physical causal claim. */ }
    occurrence passiveQuiet : Event { attribute :>> description = "A quiet target provides no usable acoustic cue before the response deadline."; }
    connection passiveQuietContributes : Causation connect passiveQuiet to exposure.missedDetection { doc /* Conditional design hypothesis for AC-01; not an installed configuration or individually sufficient physical causal claim. */ }
    occurrence passiveAmbiguous : Event { attribute :>> description = "Flow noise, multipath or calibration error produces a plausible wrong bearing or motion estimate."; }
    connection passiveAmbiguousContributes : Causation connect passiveAmbiguous to exposure.wrongMotionPrediction { doc /* Conditional design hypothesis for AC-01; not an installed configuration or individually sufficient physical causal claim. */ }
    occurrence activeClutter : Event { attribute :>> description = "Bubbles, clutter, shadowing or weak target return removes required sonar detection."; }
    connection activeClutterContributes : Causation connect activeClutter to exposure.missedDetection { doc /* Conditional design hypothesis for AC-02 / AC-03; not an installed configuration or individually sufficient physical causal claim. */ }
    occurrence narrowBeamRevisit : Event { attribute :>> description = "Motion-dependent narrow-beam coverage leaves a target unsampled too long."; }
    connection narrowBeamRevisitContributes : Causation connect narrowBeamRevisit to exposure.lateObservation { doc /* Conditional design hypothesis for AC-02; not an installed configuration or individually sufficient physical causal claim. */ }
    occurrence multibeamExtent : Event { attribute :>> description = "A sonar return is treated as complete rider, rig or line extent when it is not."; }
    connection multibeamExtentContributes : Causation connect multibeamExtent to exposure.wrongMotionPrediction { doc /* Conditional design hypothesis for AC-03; not an installed configuration or individually sufficient physical causal claim. */ }
    occurrence invertedMount : Event { attribute :>> description = "Capsize immerses optical apertures or exposes acoustic heads, defeating the credited fallback."; }
    connection invertedMountContributes : Causation connect invertedMount to exposure.inadequateRecoveryObservation { doc /* Conditional design hypothesis for All concepts; not an installed configuration or individually sufficient physical causal claim. */ }
    occurrence wingDriveJam : Event { attribute :>> description = "A wing drive or bearing jams at an adverse force direction during avoidance."; }
    connection wingDriveJamContributes : Causation connect wingDriveJam to exposure.sailControlUnavailable { doc /* Conditional design hypothesis for Rigid-wing alternatives; not an installed configuration or individually sufficient physical causal claim. */ }
    occurrence softSailSheetJam : Event { attribute :>> description = "A sheet or sail mechanism jams so commanded force reduction is not achieved."; }
    connection softSailSheetJamContributes : Causation connect softSailSheetJam to exposure.sailControlUnavailable { doc /* Conditional design hypothesis for Soft-sail alternative; not an installed configuration or individually sufficient physical causal claim. */ }
    part functional : FailureAnalysis::Review { ref part :>> system = BlueDog::Architecture::missionContext.boat; attribute :>> scopeReviewed = false;
        part missedDetection : FailureAnalysis::ReviewRow subsets modes {
            ref part :>> affected = BlueDog::Architecture::missionContext.boat.control.collisionAvoidance;
            attribute :>> identifier = "AF-001"; attribute :>> intendedFunction = "Observe traffic";
            occurrence initiatingCause : Event { attribute :>> description = "Sensor coverage or sensitivity is inadequate for the admitted target and conditions."; }
            ref occurrence :>> cause = initiatingCause;
            ref occurrence :>> failureMode = exposure.missedDetection; ref occurrence :>> localEffect = exposure.OR_observationUnavailable; ref occurrence :>> missionEffect = exposure.AND_safeSeparationUnsupported;
            attribute :>> proposedDetection = "Coverage confidence and independent observation are unproven."; attribute :>> recommendedAction = "Demonstrate class-specific timely observation and explicit unknown-target treatment."; attribute :>> ownerRole = "Perception"; attribute :>> safetyCritical = true;
        }
        part lateObservation : FailureAnalysis::ReviewRow subsets modes {
            ref part :>> affected = BlueDog::Architecture::missionContext.boat.control.collisionAvoidance;
            attribute :>> identifier = "AF-002"; attribute :>> intendedFunction = "Deliver timely tracks";
            occurrence initiatingCause : Event { attribute :>> description = "Acquisition, transport, processing or sector revisit exceeds the response budget."; }
            ref occurrence :>> cause = initiatingCause;
            ref occurrence :>> failureMode = exposure.lateObservation; ref occurrence :>> localEffect = exposure.OR_observationUnavailable; ref occurrence :>> missionEffect = exposure.AND_safeSeparationUnsupported;
            attribute :>> proposedDetection = "Capture-time and end-to-end age monitoring are proposed."; attribute :>> recommendedAction = "Inject latency and stale timestamps at the encounter boundary."; attribute :>> ownerRole = "Perception"; attribute :>> safetyCritical = true;
        }
        part falseOrSwappedTrack : FailureAnalysis::ReviewRow subsets modes {
            ref part :>> affected = BlueDog::Architecture::missionContext.boat.control.collisionAvoidance;
            attribute :>> identifier = "AF-003"; attribute :>> intendedFunction = "Maintain target identity";
            occurrence initiatingCause : Event { attribute :>> description = "Clutter or association errors transfer motion or duty to the wrong object."; }
            ref occurrence :>> cause = initiatingCause;
            ref occurrence :>> failureMode = exposure.falseOrSwappedTrack; ref occurrence :>> localEffect = exposure.OR_observationUnavailable; ref occurrence :>> missionEffect = exposure.AND_safeSeparationUnsupported;
            attribute :>> proposedDetection = "Association ambiguity detection is unproven."; attribute :>> recommendedAction = "Exercise crossing tracks, groups, disappearances and reappearance without erasing duties."; attribute :>> ownerRole = "Perception"; attribute :>> safetyCritical = true;
        }
        part wrongClassification : FailureAnalysis::ReviewRow subsets modes {
            ref part :>> affected = BlueDog::Architecture::missionContext.boat.control.collisionAvoidance;
            attribute :>> identifier = "AF-004"; attribute :>> intendedFunction = "Assess vessel and occupant status";
            occurrence initiatingCause : Event { attribute :>> description = "An uncertain class, tack, rider fall or propulsion mode is overcredited."; }
            ref occurrence :>> cause = initiatingCause;
            ref occurrence :>> failureMode = exposure.wrongClassification; ref occurrence :>> localEffect = exposure.OR_assessmentWrong; ref occurrence :>> missionEffect = exposure.AND_safeSeparationUnsupported;
            attribute :>> proposedDetection = "Confidence and consistency checks are proposed."; attribute :>> recommendedAction = "Inject wrong-but-plausible classifications and occupant transitions."; attribute :>> ownerRole = "Autonomy"; attribute :>> safetyCritical = true;
        }
        part wrongMotionPrediction : FailureAnalysis::ReviewRow subsets modes {
            ref part :>> affected = BlueDog::Architecture::missionContext.boat.control.collisionAvoidance;
            attribute :>> identifier = "AF-005"; attribute :>> intendedFunction = "Predict occupied water";
            occurrence initiatingCause : Event { attribute :>> description = "Turning targets, kite lines or rider falls violate the assumed trajectory or extent."; }
            ref occurrence :>> cause = initiatingCause;
            ref occurrence :>> failureMode = exposure.wrongMotionPrediction; ref occurrence :>> localEffect = exposure.OR_assessmentWrong; ref occurrence :>> missionEffect = exposure.AND_safeSeparationUnsupported;
            attribute :>> proposedDetection = "Prediction residual monitoring is proposed."; attribute :>> recommendedAction = "Bound swept extents and adversarial target maneuvers; include occupied ownship turns."; attribute :>> ownerRole = "Autonomy"; attribute :>> safetyCritical = true;
        }
        part wrongRuleAssessment : FailureAnalysis::ReviewRow subsets modes {
            ref part :>> affected = BlueDog::Architecture::missionContext.boat.control.collisionAvoidance;
            attribute :>> identifier = "AF-006"; attribute :>> intendedFunction = "Determine navigation duties";
            occurrence initiatingCause : Event { attribute :>> description = "Context, overtaking memory or stand-on escalation is misapplied."; }
            ref occurrence :>> cause = initiatingCause;
            ref occurrence :>> failureMode = exposure.wrongRuleAssessment; ref occurrence :>> localEffect = exposure.OR_assessmentWrong; ref occurrence :>> missionEffect = exposure.AND_safeSeparationUnsupported;
            attribute :>> proposedDetection = "Native rule consistency checks cover only supplied facts."; attribute :>> recommendedAction = "Inject context changes, missing tracks and inconsistent facts; test retained duties."; attribute :>> ownerRole = "Autonomy"; attribute :>> safetyCritical = true;
        }
        part noFeasibleCommand : FailureAnalysis::ReviewRow subsets modes {
            ref part :>> affected = BlueDog::Architecture::missionContext.boat.control.collisionAvoidance;
            attribute :>> identifier = "AF-007"; attribute :>> intendedFunction = "Select a safe response";
            occurrence initiatingCause : Event { attribute :>> description = "Required clearance, duties and achieved maneuver capability leave no admissible command."; }
            ref occurrence :>> cause = initiatingCause;
            ref occurrence :>> failureMode = exposure.noFeasibleCommand; ref occurrence :>> localEffect = exposure.OR_commandUnsafe; ref occurrence :>> missionEffect = exposure.AND_safeSeparationUnsupported;
            attribute :>> proposedDetection = "Feasibility rejection exists only in bounded replay."; attribute :>> recommendedAction = "Verify rejection timing and a safe transition when no candidate remains."; attribute :>> ownerRole = "Guidance"; attribute :>> safetyCritical = true;
        }
        part unsafeCourtesyChange : FailureAnalysis::ReviewRow subsets modes {
            ref part :>> affected = BlueDog::Architecture::missionContext.boat.control.collisionAvoidance;
            attribute :>> identifier = "AF-008"; attribute :>> intendedFunction = "Remain predictable";
            occurrence initiatingCause : Event { attribute :>> description = "Early route preference is applied as a late always-yield maneuver."; }
            ref occurrence :>> cause = initiatingCause;
            ref occurrence :>> failureMode = exposure.unsafeCourtesyChange; ref occurrence :>> localEffect = exposure.OR_commandUnsafe; ref occurrence :>> missionEffect = exposure.AND_safeSeparationUnsupported;
            attribute :>> proposedDetection = "Rule-consistency filtering is proposed for the future planner."; attribute :>> recommendedAction = "Test that courtesy cannot override established encounter duties or create another conflict."; attribute :>> ownerRole = "Guidance"; attribute :>> safetyCritical = true;
        }
        part steeringUnavailable : FailureAnalysis::ReviewRow subsets modes {
            ref part :>> affected = BlueDog::Architecture::missionContext.boat.control.collisionAvoidance;
            attribute :>> identifier = "AF-009"; attribute :>> intendedFunction = "Execute heading response";
            occurrence initiatingCause : Event { attribute :>> description = "Weeds, linkage damage or actuator saturation defeats steering."; }
            ref occurrence :>> cause = initiatingCause;
            ref occurrence :>> failureMode = exposure.steeringUnavailable; ref occurrence :>> localEffect = exposure.OR_maneuverUnavailable; ref occurrence :>> missionEffect = exposure.AND_safeSeparationUnsupported;
            attribute :>> proposedDetection = "Command/position/current and motion residuals are unproven."; attribute :>> recommendedAction = "Measure jammed and reduced-authority trajectories and response limits."; attribute :>> ownerRole = "Actuation"; attribute :>> safetyCritical = true;
        }
        part sailControlUnavailable : FailureAnalysis::ReviewRow subsets modes {
            ref part :>> affected = BlueDog::Architecture::missionContext.boat.control.collisionAvoidance;
            attribute :>> identifier = "AF-010"; attribute :>> intendedFunction = "Execute force response";
            occurrence initiatingCause : Event { attribute :>> description = "Rig actuator or sail mechanism jams or lacks authority."; }
            ref occurrence :>> cause = initiatingCause;
            ref occurrence :>> failureMode = exposure.sailControlUnavailable; ref occurrence :>> localEffect = exposure.OR_maneuverUnavailable; ref occurrence :>> missionEffect = exposure.AND_safeSeparationUnsupported;
            attribute :>> proposedDetection = "Trim and achieved-force monitoring are unproven."; attribute :>> recommendedAction = "Compare failure positions across all three rigs and test adverse trim."; attribute :>> ownerRole = "Rig/control"; attribute :>> safetyCritical = true;
        }
        part unobservedExecutionError : FailureAnalysis::ReviewRow subsets modes {
            ref part :>> affected = BlueDog::Architecture::missionContext.boat.control.collisionAvoidance;
            attribute :>> identifier = "AF-011"; attribute :>> intendedFunction = "Monitor achieved response";
            occurrence initiatingCause : Event { attribute :>> description = "Guidance assumes commanded motion despite current, stall, latency or drift."; }
            ref occurrence :>> cause = initiatingCause;
            ref occurrence :>> failureMode = exposure.unobservedExecutionError; ref occurrence :>> localEffect = exposure.OR_maneuverUnavailable; ref occurrence :>> missionEffect = exposure.AND_safeSeparationUnsupported;
            attribute :>> proposedDetection = "Independent trajectory residual monitoring is unproven."; attribute :>> recommendedAction = "Inject motion mismatch and test timely replanning with actual achieved motion."; attribute :>> ownerRole = "Navigation/control"; attribute :>> safetyCritical = true;
        }
        part unsafeAbortTransition : FailureAnalysis::ReviewRow subsets modes {
            ref part :>> affected = BlueDog::Architecture::missionContext.boat.control.collisionAvoidance;
            attribute :>> identifier = "AF-012"; attribute :>> intendedFunction = "Transition safely to recovery";
            occurrence initiatingCause : Event { attribute :>> description = "Command arbitration, reset or propulsion gating loses safety during abort."; }
            ref occurrence :>> cause = initiatingCause;
            ref occurrence :>> failureMode = exposure.unsafeAbortTransition; ref occurrence :>> localEffect = exposure.OR_recoveryUnavailable; ref occurrence :>> missionEffect = exposure.AND_safeSeparationUnsupported;
            attribute :>> proposedDetection = "Qualification latch tests do not establish safe motion."; attribute :>> recommendedAction = "Inject simultaneous abort, reset and stale commands; verify navigation duties in recovery."; attribute :>> ownerRole = "System/control"; attribute :>> safetyCritical = true;
        }
        part inadequateRecoveryObservation : FailureAnalysis::ReviewRow subsets modes {
            ref part :>> affected = BlueDog::Architecture::missionContext.boat.control.collisionAvoidance;
            attribute :>> identifier = "AF-013"; attribute :>> intendedFunction = "Preserve fallback awareness";
            occurrence initiatingCause : Event { attribute :>> description = "Primary and fallback share failed sensors or lack usable casualty geometry."; }
            ref occurrence :>> cause = initiatingCause;
            ref occurrence :>> failureMode = exposure.inadequateRecoveryObservation; ref occurrence :>> localEffect = exposure.OR_recoveryUnavailable; ref occurrence :>> missionEffect = exposure.AND_safeSeparationUnsupported;
            attribute :>> proposedDetection = "Independent recovery observation is not selected."; attribute :>> recommendedAction = "Design and demonstrate complete power, host, observation and navigation independence."; attribute :>> ownerRole = "System integration"; attribute :>> safetyCritical = true;
        }
        part noSafeRecoveryRoute : FailureAnalysis::ReviewRow subsets modes {
            ref part :>> affected = BlueDog::Architecture::missionContext.boat.control.collisionAvoidance;
            attribute :>> identifier = "AF-014"; attribute :>> intendedFunction = "Choose a safe fallback path";
            occurrence initiatingCause : Event { attribute :>> description = "Remaining motion, traffic or boundaries invalidate shore access."; }
            ref occurrence :>> cause = initiatingCause;
            ref occurrence :>> failureMode = exposure.noSafeRecoveryRoute; ref occurrence :>> localEffect = exposure.OR_recoveryUnavailable; ref occurrence :>> missionEffect = exposure.AND_safeSeparationUnsupported;
            attribute :>> proposedDetection = "Geometric recovery checks do not establish rule compliance."; attribute :>> recommendedAction = "Exercise blocked routes, lost sensing and no safe transit without assuming motor use is safe."; attribute :>> ownerRole = "Recovery"; attribute :>> safetyCritical = true;
        }
        part recoveryTooLate : FailureAnalysis::ReviewRow subsets modes {
            ref part :>> affected = BlueDog::Architecture::missionContext.boat.control.collisionAvoidance;
            attribute :>> identifier = "AF-015"; attribute :>> intendedFunction = "Respond before separation is lost";
            occurrence initiatingCause : Event { attribute :>> description = "Detection, transition and recovery maneuver exceed available time."; }
            ref occurrence :>> cause = initiatingCause;
            ref occurrence :>> failureMode = exposure.recoveryTooLate; ref occurrence :>> localEffect = exposure.OR_recoveryUnavailable; ref occurrence :>> missionEffect = exposure.AND_safeSeparationUnsupported;
            attribute :>> proposedDetection = "End-to-end timing bounds are unmeasured."; attribute :>> recommendedAction = "Measure full transition latency and action effectiveness against the encounter deadline."; attribute :>> ownerRole = "Recovery"; attribute :>> safetyCritical = true;
        }
        part sharedPowerLoss : FailureAnalysis::ReviewRow subsets modes {
            ref part :>> affected = BlueDog::Architecture::missionContext.boat.control.collisionAvoidance;
            attribute :>> identifier = "AF-016"; attribute :>> intendedFunction = "Preserve independent safety power";
            occurrence initiatingCause : Event { attribute :>> description = "One bus, regulator, ingress path or wiring fault disables both responses."; }
            ref occurrence :>> cause = initiatingCause;
            ref occurrence :>> failureMode = exposure.sharedPowerLoss; ref occurrence :>> localEffect = exposure.OR_primaryUnavailable; ref occurrence :>> missionEffect = exposure.AND_safeSeparationUnsupported;
            attribute :>> proposedDetection = "Independent health detection is unresolved."; attribute :>> recommendedAction = "Inject common faults and verify physical isolation across primary and recovery."; attribute :>> ownerRole = "Power/system"; attribute :>> safetyCritical = true;
        }
        part sharedComputeLoss : FailureAnalysis::ReviewRow subsets modes {
            ref part :>> affected = BlueDog::Architecture::missionContext.boat.control.collisionAvoidance;
            attribute :>> identifier = "AF-017"; attribute :>> intendedFunction = "Preserve independent decision paths";
            occurrence initiatingCause : Event { attribute :>> description = "Shared host, clock, network or software fault corrupts both responses."; }
            ref occurrence :>> cause = initiatingCause;
            ref occurrence :>> failureMode = exposure.sharedComputeLoss; ref occurrence :>> localEffect = exposure.OR_primaryUnavailable; ref occurrence :>> missionEffect = exposure.AND_safeSeparationUnsupported;
            attribute :>> proposedDetection = "An independent monitoring path is unresolved."; attribute :>> recommendedAction = "Audit dependencies and inject frozen time, corrupt data and common reset."; attribute :>> ownerRole = "Compute/system"; attribute :>> safetyCritical = true;
        }
    }
    connection missedDetectionInitiation : Causation connect functional.missedDetection.initiatingCause to exposure.missedDetection;
    connection lateObservationInitiation : Causation connect functional.lateObservation.initiatingCause to exposure.lateObservation;
    connection falseOrSwappedTrackInitiation : Causation connect functional.falseOrSwappedTrack.initiatingCause to exposure.falseOrSwappedTrack;
    connection wrongClassificationInitiation : Causation connect functional.wrongClassification.initiatingCause to exposure.wrongClassification;
    connection wrongMotionPredictionInitiation : Causation connect functional.wrongMotionPrediction.initiatingCause to exposure.wrongMotionPrediction;
    connection wrongRuleAssessmentInitiation : Causation connect functional.wrongRuleAssessment.initiatingCause to exposure.wrongRuleAssessment;
    connection noFeasibleCommandInitiation : Causation connect functional.noFeasibleCommand.initiatingCause to exposure.noFeasibleCommand;
    connection unsafeCourtesyChangeInitiation : Causation connect functional.unsafeCourtesyChange.initiatingCause to exposure.unsafeCourtesyChange;
    connection steeringUnavailableInitiation : Causation connect functional.steeringUnavailable.initiatingCause to exposure.steeringUnavailable;
    connection sailControlUnavailableInitiation : Causation connect functional.sailControlUnavailable.initiatingCause to exposure.sailControlUnavailable;
    connection unobservedExecutionErrorInitiation : Causation connect functional.unobservedExecutionError.initiatingCause to exposure.unobservedExecutionError;
    connection unsafeAbortTransitionInitiation : Causation connect functional.unsafeAbortTransition.initiatingCause to exposure.unsafeAbortTransition;
    connection inadequateRecoveryObservationInitiation : Causation connect functional.inadequateRecoveryObservation.initiatingCause to exposure.inadequateRecoveryObservation;
    connection noSafeRecoveryRouteInitiation : Causation connect functional.noSafeRecoveryRoute.initiatingCause to exposure.noSafeRecoveryRoute;
    connection recoveryTooLateInitiation : Causation connect functional.recoveryTooLate.initiatingCause to exposure.recoveryTooLate;
    connection sharedPowerLossInitiation : Causation connect functional.sharedPowerLoss.initiatingCause to exposure.sharedPowerLoss;
    connection sharedComputeLossInitiation : Causation connect functional.sharedComputeLoss.initiatingCause to exposure.sharedComputeLoss;
    part concepts : FailureAnalysis::Review { ref part :>> system = BlueDog::Architecture::missionContext.boat; attribute :>> scopeReviewed = false;
        part fixedAngularGap : FailureAnalysis::ReviewRow subsets modes {
            ref part :>> affected = BlueDogSensingEquipment::fixedHighResolution; attribute :>> identifier = "ACF-001";
            attribute :>> intendedFunction = "SC-01 / SC-02: preserve the credited observation or maneuver capability";
            ref occurrence :>> cause = BlueDogAvoidanceFailures::fixedAngularGap; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Map installed coverage through rig trim, heel and target elevation; test seam crossings."; attribute :>> ownerRole = "Optical installation"; attribute :>> safetyCritical = true;
        }
        part fixedStaleFrames : FailureAnalysis::ReviewRow subsets modes {
            ref part :>> affected = BlueDogSensingEquipment::fixedGlobalShutter; attribute :>> identifier = "ACF-002";
            attribute :>> intendedFunction = "SC-01 / SC-02: preserve the credited observation or maneuver capability";
            ref occurrence :>> cause = BlueDogAvoidanceFailures::fixedStaleFrames; ref occurrence :>> failureMode = exposure.lateObservation; ref occurrence :>> localEffect = exposure.lateObservation; ref occurrence :>> missionEffect = exposure.AND_safeSeparationUnsupported;
            attribute :>> proposedDetection = "Proposed diagnostics and degraded behavior require installed evidence.";
            attribute :>> recommendedAction = "Inject frozen images and capture/processing delay; verify end-to-end age, not receipt time."; attribute :>> ownerRole = "Perception/software"; attribute :>> safetyCritical = true;
        }
        part wetOptics : FailureAnalysis::ReviewRow subsets modes {
            ref part :>> affected = BlueDogSensingEquipment::fixedHighResolution; attribute :>> identifier = "ACF-003";
            attribute :>> intendedFunction = "SC-01 / SC-02 / SC-03: preserve the credited observation or maneuver capability";
            ref occurrence :>> cause = BlueDogAvoidanceFailures::wetOptics; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Wet/glare/night trials; test degradation detection and safe admission limits."; attribute :>> ownerRole = "Optical installation"; attribute :>> safetyCritical = true;
        }
        part sharedHub : FailureAnalysis::ReviewRow subsets modes {
            ref part :>> affected = BlueDogSensingEquipment::scanningCamera; attribute :>> identifier = "ACF-004";
            attribute :>> intendedFunction = "SC-01 / SC-02 / SC-03: preserve the credited observation or maneuver capability";
            ref occurrence :>> cause = BlueDogAvoidanceFailures::sharedHub; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Fault the hub/host and check isolation; do not credit camera count as independence."; attribute :>> ownerRole = "Compute/power"; attribute :>> safetyCritical = true;
        }
        part scannerJam : FailureAnalysis::ReviewRow subsets modes {
            ref part :>> affected = BlueDogSensingEquipment::scanningCamera; attribute :>> identifier = "ACF-005";
            attribute :>> intendedFunction = "SC-03: preserve the credited observation or maneuver capability";
            ref occurrence :>> cause = BlueDogAvoidanceFailures::scannerJam; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Jam the drive; inject encoder disagreement and verify sector-age monitoring."; attribute :>> ownerRole = "Scanning installation"; attribute :>> safetyCritical = true;
        }
        part scannerRevisit : FailureAnalysis::ReviewRow subsets modes {
            ref part :>> affected = BlueDogSensingEquipment::scanningCamera; attribute :>> identifier = "ACF-006";
            attribute :>> intendedFunction = "SC-03: preserve the credited observation or maneuver capability";
            ref occurrence :>> cause = BlueDogAvoidanceFailures::scannerRevisit; ref occurrence :>> failureMode = exposure.lateObservation; ref occurrence :>> localEffect = exposure.lateObservation; ref occurrence :>> missionEffect = exposure.AND_safeSeparationUnsupported;
            attribute :>> proposedDetection = "Proposed diagnostics and degraded behavior require installed evidence.";
            attribute :>> recommendedAction = "Measure worst-case target revisit and track age during reversal and occupied turns."; attribute :>> ownerRole = "Scanning installation"; attribute :>> safetyCritical = true;
        }
        part scannerCable : FailureAnalysis::ReviewRow subsets modes {
            ref part :>> affected = BlueDogSensingEquipment::scanningCamera; attribute :>> identifier = "ACF-007";
            attribute :>> intendedFunction = "SC-03: preserve the credited observation or maneuver capability";
            ref occurrence :>> cause = BlueDogAvoidanceFailures::scannerCable; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Wet-cycle the complete mount and cable path; demonstrate stall detection."; attribute :>> ownerRole = "Scanning installation"; attribute :>> safetyCritical = true;
        }
        part passiveQuiet : FailureAnalysis::ReviewRow subsets modes {
            ref part :>> affected = BlueDogAcousticEquipment::passiveArray; attribute :>> identifier = "ACF-008";
            attribute :>> intendedFunction = "AC-01: preserve the credited observation or maneuver capability";
            ref occurrence :>> cause = BlueDogAvoidanceFailures::passiveQuiet; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Retain nonacoustic coverage for quiet hazards; measure class-specific cue availability."; attribute :>> ownerRole = "Acoustics"; attribute :>> safetyCritical = true;
        }
        part passiveAmbiguous : FailureAnalysis::ReviewRow subsets modes {
            ref part :>> affected = BlueDogAcousticEquipment::passiveArray; attribute :>> identifier = "ACF-009";
            attribute :>> intendedFunction = "AC-01: preserve the credited observation or maneuver capability";
            ref occurrence :>> cause = BlueDogAvoidanceFailures::passiveAmbiguous; ref occurrence :>> failureMode = exposure.wrongMotionPrediction; ref occurrence :>> localEffect = exposure.wrongMotionPrediction; ref occurrence :>> missionEffect = exposure.AND_safeSeparationUnsupported;
            attribute :>> proposedDetection = "Proposed diagnostics and degraded behavior require installed evidence.";
            attribute :>> recommendedAction = "Calibrate channel phase/geometry and test self-noise and multipath; do not infer range from amplitude."; attribute :>> ownerRole = "Acoustics"; attribute :>> safetyCritical = true;
        }
        part activeClutter : FailureAnalysis::ReviewRow subsets modes {
            ref part :>> affected = BlueDogAcousticEquipment::multibeamForward; attribute :>> identifier = "ACF-010";
            attribute :>> intendedFunction = "AC-02 / AC-03: preserve the credited observation or maneuver capability";
            ref occurrence :>> cause = BlueDogAvoidanceFailures::activeClutter; ref occurrence :>> failureMode = exposure.missedDetection; ref occurrence :>> localEffect = exposure.missedDetection; ref occurrence :>> missionEffect = exposure.AND_safeSeparationUnsupported;
            attribute :>> proposedDetection = "Proposed diagnostics and degraded behavior require installed evidence.";
            attribute :>> recommendedAction = "Measure target-class performance under bubbles, weeds, waves and bottom clutter."; attribute :>> ownerRole = "Acoustics"; attribute :>> safetyCritical = true;
        }
        part narrowBeamRevisit : FailureAnalysis::ReviewRow subsets modes {
            ref part :>> affected = BlueDogAcousticEquipment::narrowBeamForward; attribute :>> identifier = "ACF-011";
            attribute :>> intendedFunction = "AC-02: preserve the credited observation or maneuver capability";
            ref occurrence :>> cause = BlueDogAvoidanceFailures::narrowBeamRevisit; ref occurrence :>> failureMode = exposure.lateObservation; ref occurrence :>> localEffect = exposure.lateObservation; ref occurrence :>> missionEffect = exposure.AND_safeSeparationUnsupported;
            attribute :>> proposedDetection = "Proposed diagnostics and degraded behavior require installed evidence.";
            attribute :>> recommendedAction = "Measure motion-aware coverage and revisit; reject stationary coverage assumptions."; attribute :>> ownerRole = "Acoustics"; attribute :>> safetyCritical = true;
        }
        part multibeamExtent : FailureAnalysis::ReviewRow subsets modes {
            ref part :>> affected = BlueDogAcousticEquipment::multibeamForward; attribute :>> identifier = "ACF-012";
            attribute :>> intendedFunction = "AC-03: preserve the credited observation or maneuver capability";
            ref occurrence :>> cause = BlueDogAvoidanceFailures::multibeamExtent; ref occurrence :>> failureMode = exposure.wrongMotionPrediction; ref occurrence :>> localEffect = exposure.wrongMotionPrediction; ref occurrence :>> missionEffect = exposure.AND_safeSeparationUnsupported;
            attribute :>> proposedDetection = "Proposed diagnostics and degraded behavior require installed evidence.";
            attribute :>> recommendedAction = "Validate swept-volume estimates with above-water rider and line geometry."; attribute :>> ownerRole = "Acoustics/perception"; attribute :>> safetyCritical = true;
        }
        part invertedMount : FailureAnalysis::ReviewRow subsets modes {
            ref part :>> affected = BlueDogSensingEquipment::scanningCamera; attribute :>> identifier = "ACF-013";
            attribute :>> intendedFunction = "All concepts: preserve the credited observation or maneuver capability";
            ref occurrence :>> cause = BlueDogAvoidanceFailures::invertedMount; ref occurrence :>> failureMode = exposure.inadequateRecoveryObservation; ref occurrence :>> localEffect = exposure.inadequateRecoveryObservation; ref occurrence :>> missionEffect = exposure.AND_safeSeparationUnsupported;
            attribute :>> proposedDetection = "Proposed diagnostics and degraded behavior require installed evidence.";
            attribute :>> recommendedAction = "Demonstrate upright/inverted installed geometry and independent recovery sensing."; attribute :>> ownerRole = "System integration"; attribute :>> safetyCritical = true;
        }
        part wingDriveJam : FailureAnalysis::ReviewRow subsets modes {
            ref part :>> affected = BlueDogSailTrade::camberedWing; attribute :>> identifier = "ACF-014";
            attribute :>> intendedFunction = "Rigid-wing alternatives: preserve the credited observation or maneuver capability";
            ref occurrence :>> cause = BlueDogAvoidanceFailures::wingDriveJam; ref occurrence :>> failureMode = exposure.sailControlUnavailable; ref occurrence :>> localEffect = exposure.sailControlUnavailable; ref occurrence :>> missionEffect = exposure.AND_safeSeparationUnsupported;
            attribute :>> proposedDetection = "Proposed diagnostics and degraded behavior require installed evidence.";
            attribute :>> recommendedAction = "Compare direct-drive and tail-controlled failure positions; verify load limiting and remaining steering."; attribute :>> ownerRole = "Rig/control"; attribute :>> safetyCritical = true;
        }
        part softSailSheetJam : FailureAnalysis::ReviewRow subsets modes {
            ref part :>> affected = BlueDogSailTrade::softSail; attribute :>> identifier = "ACF-015";
            attribute :>> intendedFunction = "Soft-sail alternative: preserve the credited observation or maneuver capability";
            ref occurrence :>> cause = BlueDogAvoidanceFailures::softSailSheetJam; ref occurrence :>> failureMode = exposure.sailControlUnavailable; ref occurrence :>> localEffect = exposure.sailControlUnavailable; ref occurrence :>> missionEffect = exposure.AND_safeSeparationUnsupported;
            attribute :>> proposedDetection = "Proposed diagnostics and degraded behavior require installed evidence.";
            attribute :>> recommendedAction = "Inject sheet jams and adverse trim; measure residual maneuver authority."; attribute :>> ownerRole = "Rig/control"; attribute :>> safetyCritical = true;
        }
    }
    dependency missedDetectionCriterion from functional::missedDetection to BlueDogRequirements::trafficSafety;
    dependency lateObservationCriterion from functional::lateObservation to BlueDogRequirements::trafficSafety;
    dependency falseOrSwappedTrackCriterion from functional::falseOrSwappedTrack to BlueDogRequirements::trafficSafety;
    dependency wrongClassificationCriterion from functional::wrongClassification to BlueDogRequirements::trafficSafety;
    dependency wrongMotionPredictionCriterion from functional::wrongMotionPrediction to BlueDogRequirements::trafficSafety;
    dependency wrongRuleAssessmentCriterion from functional::wrongRuleAssessment to BlueDogRequirements::trafficSafety;
    dependency noFeasibleCommandCriterion from functional::noFeasibleCommand to BlueDogRequirements::trafficSafety;
    dependency unsafeCourtesyChangeCriterion from functional::unsafeCourtesyChange to BlueDogRequirements::trafficSafety;
    dependency steeringUnavailableCriterion from functional::steeringUnavailable to BlueDogRequirements::trafficSafety;
    dependency sailControlUnavailableCriterion from functional::sailControlUnavailable to BlueDogRequirements::trafficSafety;
    dependency unobservedExecutionErrorCriterion from functional::unobservedExecutionError to BlueDogRequirements::trafficSafety;
    dependency unsafeAbortTransitionCriterion from functional::unsafeAbortTransition to BlueDogRequirements::trafficSafety;
    dependency inadequateRecoveryObservationCriterion from functional::inadequateRecoveryObservation to BlueDogRequirements::trafficSafety;
    dependency noSafeRecoveryRouteCriterion from functional::noSafeRecoveryRoute to BlueDogRequirements::trafficSafety;
    dependency recoveryTooLateCriterion from functional::recoveryTooLate to BlueDogRequirements::trafficSafety;
    dependency sharedPowerLossCriterion from functional::sharedPowerLoss to BlueDogRequirements::trafficSafety;
    dependency sharedComputeLossCriterion from functional::sharedComputeLoss to BlueDogRequirements::trafficSafety;
    dependency navigationDuties from functional::wrongRuleAssessment to GorgeChallenge::navigationRules;
    dependency courtesyPolicy from functional::unsafeCourtesyChange to BlueDogDesignDecisions::trafficCourtesy;
    dependency fallbackPolicy from functional::unsafeAbortTransition to GorgeChallenge::safetyCapabilityAbort;
    dependency starterLink from functional to BlueDogDFMEA::starter::trafficMiss;
    occurrence OR_fixedObservationUnavailable : OrGate { doc /* Conditional branch for SC-01 or SC-02 only; other concepts are alternatives, not installed backups. No physical failure rates or safeguards are credited. */ attribute :>> description = "Required concept observation or cue unavailable within the response interval"; ref occurrence :>> inputs = (fixedAngularGap, fixedStaleFrames, wetOptics, sharedHub); }
    connection OR_fixedObservationUnavailable_0 : Causation connect fixedAngularGap to OR_fixedObservationUnavailable { metadata CausationMetadata { isSufficient = true; } }
    connection OR_fixedObservationUnavailable_1 : Causation connect fixedStaleFrames to OR_fixedObservationUnavailable { metadata CausationMetadata { isSufficient = true; } }
    connection OR_fixedObservationUnavailable_2 : Causation connect wetOptics to OR_fixedObservationUnavailable { metadata CausationMetadata { isSufficient = true; } }
    connection OR_fixedObservationUnavailable_3 : Causation connect sharedHub to OR_fixedObservationUnavailable { metadata CausationMetadata { isSufficient = true; } }
    occurrence <'Scanner observation unavailable'> OR_scannerObservationUnavailable : OrGate { doc /* Conditional branch for SC-03 only; other concepts are alternatives, not installed backups. No physical failure rates or safeguards are credited. */ attribute :>> description = "Required concept observation or cue unavailable within the response interval"; ref occurrence :>> inputs = (scannerJam, scannerRevisit, scannerCable, wetOptics, sharedHub); }
    connection OR_scannerObservationUnavailable_0 : Causation connect scannerJam to OR_scannerObservationUnavailable { metadata CausationMetadata { isSufficient = true; } }
    connection OR_scannerObservationUnavailable_1 : Causation connect scannerRevisit to OR_scannerObservationUnavailable { metadata CausationMetadata { isSufficient = true; } }
    connection OR_scannerObservationUnavailable_2 : Causation connect scannerCable to OR_scannerObservationUnavailable { metadata CausationMetadata { isSufficient = true; } }
    connection OR_scannerObservationUnavailable_3 : Causation connect wetOptics to OR_scannerObservationUnavailable { metadata CausationMetadata { isSufficient = true; } }
    connection OR_scannerObservationUnavailable_4 : Causation connect sharedHub to OR_scannerObservationUnavailable { metadata CausationMetadata { isSufficient = true; } }
    occurrence OR_passiveCueUnavailable : OrGate { doc /* Conditional branch for AC-01 only; other concepts are alternatives, not installed backups. No physical failure rates or safeguards are credited. */ attribute :>> description = "Required concept observation or cue unavailable within the response interval"; ref occurrence :>> inputs = (passiveQuiet, passiveAmbiguous, invertedMount); }
    connection OR_passiveCueUnavailable_0 : Causation connect passiveQuiet to OR_passiveCueUnavailable { metadata CausationMetadata { isSufficient = true; } }
    connection OR_passiveCueUnavailable_1 : Causation connect passiveAmbiguous to OR_passiveCueUnavailable { metadata CausationMetadata { isSufficient = true; } }
    connection OR_passiveCueUnavailable_2 : Causation connect invertedMount to OR_passiveCueUnavailable { metadata CausationMetadata { isSufficient = true; } }
    dependency fixedAngularGap_fixedGlobalShutter from concepts::fixedAngularGap to BlueDogSensingEquipment::fixedGlobalShutter;
    dependency wetOptics_fixedGlobalShutter from concepts::wetOptics to BlueDogSensingEquipment::fixedGlobalShutter;
    dependency wetOptics_scanningCamera from concepts::wetOptics to BlueDogSensingEquipment::scanningCamera;
    dependency sharedHub_fixedHighResolution from concepts::sharedHub to BlueDogSensingEquipment::fixedHighResolution;
    dependency sharedHub_fixedGlobalShutter from concepts::sharedHub to BlueDogSensingEquipment::fixedGlobalShutter;
    dependency activeNarrowScope from concepts::activeClutter to BlueDogAcousticEquipment::narrowBeamForward;
    dependency wingTailScope from concepts::wingDriveJam to BlueDogSailTrade::tailWing;
    dependency inverted_fixedHighResolution from concepts::invertedMount to BlueDogSensingEquipment::fixedHighResolution;
    dependency inverted_fixedGlobalShutter from concepts::invertedMount to BlueDogSensingEquipment::fixedGlobalShutter;
    dependency inverted_passiveArray from concepts::invertedMount to BlueDogAcousticEquipment::passiveArray;
    dependency inverted_narrowBeamForward from concepts::invertedMount to BlueDogAcousticEquipment::narrowBeamForward;
    dependency inverted_multibeamForward from concepts::invertedMount to BlueDogAcousticEquipment::multibeamForward;
}

package BlueDogCandidateEnergy {
    private import ScalarValues::*;
    private import BlueDogSRRCurrent::energyInputs;
    private import BlueDogSRRCurrent::candidate;
    private import BlueDogSRRCurrent::energyGoverningCase;
    private import BlueDogSRRCurrent::peakGoverningCase;
    doc /* Authoritative accounting for the retained 440 Wh candidate's archived
     * nominal finite-passage screen. Inputs are projected from its source revision
     * and immutable replay; this is not an installed equipment qualification.
     * No independent electronics component split or perception capability is credited. */
    attribute exposureHours : Real = candidate.westerlyPassageHours*energyInputs.durationMultiplier+energyInputs.delayHours;
    attribute wingAverageCase : Real [3] ordered nonunique = MarineActuation::DrivePower(energyGoverningCase.wingTorqueNm,energyInputs.wingRateRadS,energyInputs.motorEfficiency,energyInputs.gearboxEfficiency,energyInputs.wingNoLoadW,energyInputs.wingControllerW,energyInputs.wingMotorHoldingW,energyInputs.wingMoveFraction,energyInputs.wingHoldingFraction);
    attribute rudderAverageCase : Real [3] ordered nonunique = MarineActuation::DrivePower(energyGoverningCase.rudderTorqueNm,energyInputs.rudderRateRadS,energyInputs.motorEfficiency,1,1,0.1,energyInputs.rudderHoldingWPerNm*energyGoverningCase.rudderTorqueNm,energyInputs.rudderMoveFraction,1-energyInputs.rudderMoveFraction);
    attribute wingPeakCase : Real [3] ordered nonunique = MarineActuation::DrivePower(peakGoverningCase.wingTorqueNm,energyInputs.wingRateRadS,energyInputs.motorEfficiency,energyInputs.gearboxEfficiency,energyInputs.wingNoLoadW,energyInputs.wingControllerW,energyInputs.wingMotorHoldingW,energyInputs.wingMoveFraction,energyInputs.wingHoldingFraction);
    attribute rudderPeakCase : Real [3] ordered nonunique = MarineActuation::DrivePower(peakGoverningCase.rudderTorqueNm,energyInputs.rudderRateRadS,energyInputs.motorEfficiency,1,1,0.1,energyInputs.rudderHoldingWPerNm*peakGoverningCase.rudderTorqueNm,energyInputs.rudderMoveFraction,1-energyInputs.rudderMoveFraction);
    part def Load {
        attribute label : String;
        attribute averageBusW : Real;
        attribute peakBusW : Real;
        attribute busWh : Real = averageBusW*exposureHours;
        attribute batteryWh : Real = busWh/energyInputs.dischargeEfficiency;
        attribute basis : String;
    }
    part electronics : Load {
        attribute :>> label = "Base electronics (unresolved component split)";
        attribute :>> averageBusW = energyInputs.electronicsW-energyInputs.windBusW;
        attribute :>> peakBusW = averageBusW;
        attribute :>> basis = "Lumped allocation; hardware, duty and surge unmeasured";
    }
    part wind : Load {
        attribute :>> label = "Wired wind sensor and interface";
        attribute :>> averageBusW = energyInputs.windBusW;
        attribute :>> peakBusW = averageBusW;
        attribute :>> basis = "Supplier sensor demand plus interface, conversion and margin allowances; startup unmeasured";
    }
    part wing : Load {
        attribute :>> label = "Wing drive and controller";
        attribute :>> averageBusW = wingAverageCase#(1);
        attribute :>> peakBusW = wingPeakCase#(2);
        attribute :>> basis = "Native torque/duty model: 2 percent moving, 98 percent holding; no motor holding current";
    }
    part rudder : Load {
        attribute :>> label = "Rudder drive and controller";
        attribute :>> averageBusW = rudderAverageCase#(1);
        attribute :>> peakBusW = rudderPeakCase#(2);
        attribute :>> basis = "Native torque/duty model: 5 percent moving, 95 percent holding";
    }
    part totals : Load {
        attribute :>> label = "Total sailing load";
        attribute :>> averageBusW = electronics.averageBusW+wind.averageBusW+wing.averageBusW+rudder.averageBusW;
        attribute :>> peakBusW = electronics.peakBusW+wind.peakBusW+wing.peakBusW+rudder.peakBusW;
        attribute :>> basis = "Maximum sampled average throughout exposure; peak uses the maximum-total-peak operating case";
    }
    part def Account { attribute label : String; attribute energyWh : Real; attribute basis : String; }
    part nominal : Account { attribute :>> label = "Nameplate battery"; attribute :>> energyWh = candidate.batteryWh; attribute :>> basis = "Allocated capacity, not measured capacity"; }
    part usable : Account { attribute :>> label = "Usable capacity"; attribute :>> energyWh = candidate.batteryWh*energyInputs.usableFraction; attribute :>> basis = "80 percent of nameplate"; }
    part departure : Account { attribute :>> label = "Departure stored energy"; attribute :>> energyWh = usable.energyWh*energyInputs.initialFraction; attribute :>> basis = "90 percent of usable capacity"; }
    part sailing : Account { attribute :>> label = "Energy delivered to sailing loads"; attribute :>> energyWh = totals.busWh; attribute :>> basis = "Average bus power times the full passage allowance"; }
    part losses : Account { attribute :>> label = "Discharge losses"; attribute :>> energyWh = totals.batteryWh-totals.busWh; attribute :>> basis = "90 percent discharge efficiency; applied once"; }
    part selfDischarge : Account { attribute :>> label = "Self-discharge"; attribute :>> energyWh = exposureHours*energyInputs.selfDischargeW; attribute :>> basis = "0.02 W battery-side withdrawal"; }
    part reserve : Account { attribute :>> label = "Protected recovery reserve"; attribute :>> energyWh = energyInputs.reserveWh; attribute :>> basis = "Synthetic allocation: 50 W motor for 0.5 h plus 8 W essentials for 2 h, times 1.2"; }
    part required : Account { attribute :>> label = "Total required at departure"; attribute :>> energyWh = totals.batteryWh+selfDischarge.energyWh+reserve.energyWh; attribute :>> basis = "Sailing withdrawal, self-discharge and reserve; zero harvest credit"; }
    part headroom : Account { attribute :>> label = "Remaining headroom"; attribute :>> energyWh = departure.energyWh-required.energyWh; attribute :>> basis = "Unallocated margin after the protected recovery reserve"; }
    part def Gap { attribute function : String; attribute allowance : String; attribute evidenceNeeded : String; }
    part compute : Gap { attribute :>> function = "Mission computer and avoidance inference"; attribute :>> allowance = "Within 4.5 W lump; no separately established allocation"; attribute :>> evidenceNeeded = "Selected pipeline, measured sustained/peak power, latency and thermal performance"; }
    part navigation : Gap { attribute :>> function = "GNSS and attitude sensing"; attribute :>> allowance = "Within 4.5 W lump; no separately established allocation"; attribute :>> evidenceNeeded = "Installed equipment and bus measurements"; }
    part traffic : Gap { attribute :>> function = "AIS, cameras, radar, hydrophones and sonar"; attribute :>> allowance = "Unselected; no incremental load or detection capability established"; attribute :>> evidenceNeeded = "Sensing trade and installed acquisition/processing power"; }
    part communications : Gap { attribute :>> function = "Telemetry, command link and recording"; attribute :>> allowance = "Within 4.5 W lump; no separately established allocation"; attribute :>> evidenceNeeded = "Transmit/receive duty, peaks and logging demand"; }
    part housekeeping : Gap { attribute :>> function = "Signals, recovery control, ingress sensing and power management"; attribute :>> allowance = "Within 4.5 W lump; no separately established allocation"; attribute :>> evidenceNeeded = "Operating modes, quiescent demand and fault independence"; }
    part recoveryHardware : Gap { attribute :>> function = "Recovery propulsion"; attribute :>> allowance = "Energy reserve allocated separately; no installed propulsion power rating established"; attribute :>> evidenceNeeded = "Measured thrust/power, casualty reachability and electrical peak capability"; }
    analysis Reconciliation {
        out attribute averageBusW : Real = totals.averageBusW;
        out attribute peakBusW : Real = totals.peakBusW;
        out attribute exposureHours : Real = BlueDogCandidateEnergy::exposureHours;
        out attribute requiredWh : Real = required.energyWh;
        out attribute departureWh : Real = departure.energyWh;
        out attribute headroomWh : Real = headroom.energyWh;
        out attribute reserveWh : Real = reserve.energyWh;
        out attribute busWh : Real = totals.busWh;
        out attribute dischargeLossWh : Real = losses.energyWh;
        out attribute selfDischargeWh : Real = selfDischarge.energyWh;
        out attribute hardwareBudgetComplete : Boolean = false;
        assert constraint { RealFunctions::abs(averageBusW-energyGoverningCase.recordedAverageW)<0.00000001 }
        assert constraint { RealFunctions::abs(peakBusW-peakGoverningCase.recordedPeakW)<0.00000001 }
        assert constraint { RealFunctions::abs(requiredWh-candidate.requiredWh)<0.00000001 }
        assert constraint { RealFunctions::abs(departureWh-candidate.departureWh)<0.00000001 }
    }
    dependency replayBasis from Reconciliation to BlueDogSRRCurrent::candidate;
    dependency driveBasis from Reconciliation to MarineActuation::DrivePower;
    dependency reserveBasis from reserve to BlueDogRequirements::lowEnergyRecovery;
}

package BlueDogClassDetection {
    doc /* Current owner-approved class-specific detection and consequence approach, 2026-10-16. No blanket 750 m floor applies to current policy. Earlier six-class and IC-01 acquisition numbers remain historical hypotheses in their original analyses. No numerical consequence, reliability or risk acceptance thresholds were selected by this policy change.*/
    private import ScalarValues::*;
    part policy {
        doc /* Detection distance must cover relative motion during observation/decision/maneuver delay, position uncertainty and reviewed clearance/margin. Consequences and exposure separately inform clearance and required reliability; do not multiply kinematic distance by severity or call a whole class harmless. Collision and nonimpediment obligations remain. No current class allocation is accepted without applicable review and evidence.*/
        attribute classIds : String [12] ordered = ("commercialTow","fishingCraft","fastCraft","sailingCraft","passengerVessel","occupiedKayak","occupiedSUP","personInWater","unoccupiedDriftingCraft","windsurfer","wingfoiler","kiter");
        attribute consequenceReview : String = "Review actual vessel mass and relative contact speed, contact geometry, rigid appendages, entanglement, capsize/immersion, occupant vulnerability and secondary collision/impediment. A low-speed glancing hull contact may have low direct damage under supported conditions; that is not a whole-class near-zero consequence allocation.";
        attribute classificationRule : String = "Before reliable classification, use a reviewed conservative envelope spanning plausible classes and occupant transitions. An apparently empty craft may have a person beside it; unknown is not unoccupied. Classification range must support the transition to a narrower envelope. With no reviewed conservative envelope, admission remains unsupported.";
        attribute reliabilityMeaning : String = "Required probability concerns timely acquisition AND sufficient track continuity for the admitted encounter class/conditions, not per-frame detector accuracy. Review exposure, false negatives, false positives and confidence basis. A lower confidence bound must come from applicable independent evidence; supplied booleans alone cannot establish acceptance.";
        attribute currentAllocationsAccepted : Boolean = false;
        attribute currentStatus : String = "Open: class clearances, consequence margins, required reliability/confidence and risk dispositions await review and evidence.";
    } part illustrative {
        doc /* Historical sensitivity inputs only: ownship 3 m/s; first five classes inherit earlier target speeds/separations. The four newly separated slow classes each reuse the former broad low-target 2 m/s and 20 m solely to show comparison arithmetic; they are not measured speeds or selected class clearances. Equal illustrated distances do not imply equal consequence or required reliability. No sensing simulation is changed.*/
        attribute targetSpeedMps : Real [9] ordered nonunique = (3.5,1.5,15,4,4,2,2,2,2);
        attribute historicalSeparationM : Real [9] ordered nonunique = (50,20,30,20,50,20,20,20,20);
        attribute ownSpeedMps : Real = 3;
        attribute positionAllowanceM : Real = 10;
        attribute responseS : Real = BlueDogEncounterEnvelope::ResponseAfterDelivery(5,1,0,1,2,15,15);
    }
    analysis def Assessment { doc /* Current class allocation/evidence gate. Required real inputs have no zero defaults. Kinematic and reviewed-design distances are not accepted deployment envelopes. Acquisition-and-track probability is separate from the whole detection-decision-maneuver response probability; no independence multiplication is assumed. Both lower confidence bounds must meet the reviewed confidence level. Method review must address sampling, correlation, uncertainty and applicability; sample count alone proves nothing. References name applicable reviewed records, not merely nonempty labels. Class-specific credit requires reliable classification; unclassified requires a reviewed conservative plausible-class envelope. allocationAccepted means supplied evidence passes this declared analysis gate, not physical qualification or full navigation-law compliance.*/ subject encounter;
        in attribute classId : String;
        in attribute classificationReliable : Boolean;
        in attribute conservativeEnvelopeReviewed : Boolean;
        in attribute classificationReviewRef : String;
        in attribute relativeSpeedBoundMps : Real;
        in attribute responseBoundS : Real;
        in attribute positionAllowanceM : Real;
        in attribute motionBoundAvailable : Boolean;
        in attribute observationBoundAvailable : Boolean;
        in attribute consequenceClearanceM : Real;
        in attribute consequenceMarginM : Real;
        in attribute consequenceReviewRef : String;
        in attribute exposureReviewRef : String;
        in attribute allocationReviewRef : String;
        in attribute requiredTimelyTrackProbability : Real;
        in attribute requiredConfidenceLevel : Real;
        in attribute reliabilityReviewRef : String;
        in attribute demonstratedRangeM : Real;
        in attribute timelyTrackProbabilityLowerBound : Real;
        in attribute evidenceConfidenceLevel : Real;
        in attribute independentEncounterCount : Integer;
        in attribute observationEvidenceRef : String;
        in attribute maneuverEvidenceRef : String;
        in attribute consequenceEvidenceRef : String;
        in attribute riskAcceptanceRef : String;
        in attribute collisionAndNonImpedimentSupported : Boolean;
        out attribute knownClass : Boolean = classId == "commercialTow" or classId == "fishingCraft" or classId == "fastCraft" or classId == "sailingCraft" or classId == "passengerVessel" or classId == "occupiedKayak" or classId == "occupiedSUP" or classId == "personInWater" or classId == "unoccupiedDriftingCraft" or classId == "windsurfer" or classId == "wingfoiler" or classId == "kiter";
        out attribute classScopeSupported : Boolean = classificationReviewRef != "" and ((knownClass and classificationReliable) or (classId == "unclassified" and conservativeEnvelopeReviewed));
        out attribute kinematicsSupported : Boolean = classScopeSupported and motionBoundAvailable and observationBoundAvailable and relativeSpeedBoundMps >= 0 and responseBoundS >= 0 and positionAllowanceM >= 0;
        out attribute kinematicMinimumM : Real = if kinematicsSupported ? relativeSpeedBoundMps*responseBoundS+positionAllowanceM else -1;
        out attribute consequenceReviewed : Boolean = consequenceReviewRef != "" and consequenceClearanceM >= 0 and consequenceMarginM >= 0;
        out attribute reliabilityCriterionReviewed : Boolean = reliabilityReviewRef != "" and requiredTimelyTrackProbability > 0 and requiredTimelyTrackProbability <= 1 and requiredConfidenceLevel > 0 and requiredConfidenceLevel < 1;
        out attribute allocationReviewed : Boolean = kinematicsSupported and consequenceReviewed and reliabilityCriterionReviewed and responseCriterionReviewed and exposureReviewRef != "" and allocationReviewRef != "";
        out attribute reviewedDesignDistanceM : Real = if allocationReviewed ? kinematicMinimumM+consequenceClearanceM+consequenceMarginM else -1;
        out attribute evidenceApplicable : Boolean = observationEvidenceRef != "" and maneuverEvidenceRef != "" and consequenceEvidenceRef != "" and evidenceMethodReviewRef != "" and independentEncounterCount > 0 and timelyTrackProbabilityLowerBound >= 0 and timelyTrackProbabilityLowerBound <= 1 and evidenceConfidenceLevel > 0 and evidenceConfidenceLevel < 1;
        out attribute reliabilitySatisfied : Boolean = allocationReviewed and evidenceApplicable and timelyTrackProbabilityLowerBound >= requiredTimelyTrackProbability and evidenceConfidenceLevel >= requiredConfidenceLevel;
        out attribute timingFeasible : Boolean = allocationReviewed and evidenceApplicable and demonstratedRangeM >= reviewedDesignDistanceM;
        out attribute allocationAccepted : Boolean = timingFeasible and reliabilitySatisfied and responseReliabilitySatisfied and collisionAndNonImpedimentSupported and riskAcceptanceRef != "" {
            doc /* Consistency gate on supplied reviewed bounds and evidence declarations only. Nonempty references are declarations: this analysis does not read or validate their contents, applicability or approval. Passing is not certification or physical qualification.*/
        }
        out attribute acceptedDetectionDistanceM : Real = if allocationAccepted ? reviewedDesignDistanceM else -1;
        out attribute physicalQualification : Boolean = false;
        out attribute status : String = if not allocationReviewed ? "Unsupported: current class allocation not reviewed" else if not allocationAccepted ? "Reviewed design distance only; safety acceptance unsupported" else "Supplied class evidence and risk disposition pass analysis gate; no physical qualification";
        in attribute requiredResponseProbability : Real;
        in attribute responseProbabilityLowerBound : Real;
        in attribute responseEvidenceConfidenceLevel : Real;
        in attribute responseEvidenceRef : String;
        in attribute responseReliabilityReviewRef : String;
        in attribute evidenceMethodReviewRef : String;
        out attribute responseReliabilitySatisfied : Boolean = allocationReviewed and responseCriterionReviewed and responseEvidenceRef != "" and evidenceMethodReviewRef != "" and responseProbabilityLowerBound >= requiredResponseProbability and responseProbabilityLowerBound <= 1 and responseEvidenceConfidenceLevel >= requiredConfidenceLevel and responseEvidenceConfidenceLevel < 1;
        out attribute responseCriterionReviewed : ScalarValues::Boolean = responseReliabilityReviewRef != "" and requiredResponseProbability > 0 and requiredResponseProbability <= 1 and requiredConfidenceLevel > 0 and requiredConfidenceLevel < 1;
    }
    analysis Summary {
        doc /* Historical nine-row sensitivity comparison; current policy additionally includes windsurfer, wingfoiler and kiter with no inherited speed or distance allocation.*/
        out attribute classIds : String [9] ordered = ("commercialTow","fishingCraft","fastCraft","sailingCraft","passengerVessel","occupiedKayak","occupiedSUP","personInWater","unoccupiedDriftingCraft");
        out attribute illustrativeTargetSpeedMps : Real [9] ordered nonunique = illustrative.targetSpeedMps;
        out attribute illustrativeSeparationM : Real [9] ordered nonunique = illustrative.historicalSeparationM;
        out attribute illustrativeResponseS : Real = illustrative.responseS;
        out attribute illustrativeKinematicMinimumM : Real [9] ordered nonunique = (1..9)->ControlFunctions::collect { in i : Integer; (illustrative.ownSpeedMps+illustrative.targetSpeedMps#(i))*illustrative.responseS+illustrative.positionAllowanceM };
        out attribute illustrativeResponseDistanceM : Real [9] ordered nonunique = (1..9)->ControlFunctions::collect { in i : Integer; (illustrative.ownSpeedMps+illustrative.targetSpeedMps#(i))*illustrative.responseS+illustrative.positionAllowanceM+illustrative.historicalSeparationM#(i) };
        out attribute currentAllocationsAccepted : Boolean = policy.currentAllocationsAccepted;
        out attribute physicalQualification : Boolean = false;
        out attribute status : String = policy.currentStatus;
    }
    dependency currentTraffic from policy to BlueDogRequirements::trafficSafety;
    dependency currentTracking from policy to BlueDogRequirements::trafficTracking;
    dependency collisionObligation from policy to GorgeChallenge::trafficCoexistence;
    dependency applicableNavigationDuties from policy to GorgeChallenge::navigationRules;
    part classRow1 {
        attribute target : String = "Commercial tow";
        attribute targetSpeedMps : Real = illustrative.targetSpeedMps#(1);
        attribute illustrativeDistanceM : Real = (illustrative.ownSpeedMps+illustrative.targetSpeedMps#(1))*illustrative.responseS+illustrative.positionAllowanceM+illustrative.historicalSeparationM#(1);
        attribute allocationAccepted : Boolean = false;
    }
    part classRow2 {
        attribute target : String = "Fishing craft";
        attribute targetSpeedMps : Real = illustrative.targetSpeedMps#(2);
        attribute illustrativeDistanceM : Real = (illustrative.ownSpeedMps+illustrative.targetSpeedMps#(2))*illustrative.responseS+illustrative.positionAllowanceM+illustrative.historicalSeparationM#(2);
        attribute allocationAccepted : Boolean = false;
    }
    part classRow3 {
        attribute target : String = "Fast craft";
        attribute targetSpeedMps : Real = illustrative.targetSpeedMps#(3);
        attribute illustrativeDistanceM : Real = (illustrative.ownSpeedMps+illustrative.targetSpeedMps#(3))*illustrative.responseS+illustrative.positionAllowanceM+illustrative.historicalSeparationM#(3);
        attribute allocationAccepted : Boolean = false;
    }
    part classRow4 {
        attribute target : String = "Sailing craft";
        attribute targetSpeedMps : Real = illustrative.targetSpeedMps#(4);
        attribute illustrativeDistanceM : Real = (illustrative.ownSpeedMps+illustrative.targetSpeedMps#(4))*illustrative.responseS+illustrative.positionAllowanceM+illustrative.historicalSeparationM#(4);
        attribute allocationAccepted : Boolean = false;
    }
    part classRow5 {
        attribute target : String = "Passenger vessel";
        attribute targetSpeedMps : Real = illustrative.targetSpeedMps#(5);
        attribute illustrativeDistanceM : Real = (illustrative.ownSpeedMps+illustrative.targetSpeedMps#(5))*illustrative.responseS+illustrative.positionAllowanceM+illustrative.historicalSeparationM#(5);
        attribute allocationAccepted : Boolean = false;
    }
    part classRow6 {
        attribute target : String = "Occupied kayak";
        attribute targetSpeedMps : Real = illustrative.targetSpeedMps#(6);
        attribute illustrativeDistanceM : Real = (illustrative.ownSpeedMps+illustrative.targetSpeedMps#(6))*illustrative.responseS+illustrative.positionAllowanceM+illustrative.historicalSeparationM#(6);
        attribute allocationAccepted : Boolean = false;
    }
    part classRow7 {
        attribute target : String = "Occupied stand-up paddleboard";
        attribute targetSpeedMps : Real = illustrative.targetSpeedMps#(7);
        attribute illustrativeDistanceM : Real = (illustrative.ownSpeedMps+illustrative.targetSpeedMps#(7))*illustrative.responseS+illustrative.positionAllowanceM+illustrative.historicalSeparationM#(7);
        attribute allocationAccepted : Boolean = false;
    }
    part classRow8 {
        attribute target : String = "Person in water";
        attribute targetSpeedMps : Real = illustrative.targetSpeedMps#(8);
        attribute illustrativeDistanceM : Real = (illustrative.ownSpeedMps+illustrative.targetSpeedMps#(8))*illustrative.responseS+illustrative.positionAllowanceM+illustrative.historicalSeparationM#(8);
        attribute allocationAccepted : Boolean = false;
    }
    part classRow9 {
        attribute target : String = "Unoccupied drifting craft";
        attribute targetSpeedMps : Real = illustrative.targetSpeedMps#(9);
        attribute illustrativeDistanceM : Real = (illustrative.ownSpeedMps+illustrative.targetSpeedMps#(9))*illustrative.responseS+illustrative.positionAllowanceM+illustrative.historicalSeparationM#(9);
        attribute allocationAccepted : Boolean = false;
    }
}

package BlueDogAnalysisCredibility {
    private import ScalarValues::*;
    metadata def UseIntent {
        attribute category : String;
        attribute intendedUse : String;
        attribute domain : String;
        attribute excludedUses : String;
        attribute evidenceNeeded : String;
    }
    metadata def Inputs :> UseIntent {
        attribute :>> category = "Inputs";
        attribute :>> intendedUse = "Export declared parameters or provisional sensitivity assumptions for an identified caller.";
        attribute :>> domain = "The owning configuration and consumer units/vector ordering; these cases export inputs, not predicted performance.";
        attribute :>> excludedUses = "No feasibility, measured uncertainty distribution or physical capability follows from exporting values.";
        attribute :>> evidenceNeeded = "Trace each value to its owner, external-data pedigree and consuming analysis; verify conversions.";
    }
    metadata def HistoricalReview :> UseIntent {
        attribute :>> category = "HistoricalReview";
        attribute :>> intendedUse = "Inspect recorded operating screens and unaccepted evidence for the original archived candidate.";
        attribute :>> domain = "Only the original run configuration, policy, source revision and sampled scenarios.";
        attribute :>> excludedUses = "No current IC-01 design substitution, physical qualification or transfer of margins between configurations.";
        attribute :>> evidenceNeeded = "Preserve archive manifests and source hashes; assess new use separately against current configuration and policy.";
    }
    metadata def Rules :> UseIntent {
        attribute :>> category = "Rules";
        attribute :>> intendedUse = "Evaluate navigation-rule obligations or fixture consistency from supplied situation facts.";
        attribute :>> domain = "Declared rule edition, delivered tracks, vessel/status/visibility/channel facts and bounded encounter context.";
        attribute :>> excludedUses = "Supplied facts do not demonstrate perception, legal status or achieved safe maneuver; no universal compliance claim.";
        attribute :>> evidenceNeeded = "Validate actual fact acquisition, rule applicability and full encounter behavior against authoritative rules and observations.";
    }
    metadata def Readiness :> UseIntent {
        attribute :>> category = "Readiness";
        attribute :>> intendedUse = "Expose missing review/evidence preconditions in the named safety or configuration argument.";
        attribute :>> domain = "Declared review scope, configuration, contributors and supplied review assertions.";
        attribute :>> excludedUses = "A true review flag or complete register does not demonstrate control effectiveness, install hardware or accept risk.";
        attribute :>> evidenceNeeded = "Actual configuration, implementation/effectiveness records, coverage review and responsible disposition evidence.";
    }
    metadata def Trade :> UseIntent {
        attribute :>> category = "Trade";
        attribute :>> intendedUse = "Compare declared rig evidence gates or illustrate a supporting buoyancy calculation.";
        attribute :>> domain = "The named candidate and ordered evidence vector, or explicit synthetic buoyancy inputs.";
        attribute :>> excludedUses = "No invented scores, hardware downselect, accepted reliability estimate or physical qualification.";
        attribute :>> evidenceNeeded = "Comparable both-tack, energy, durability, construction, casualty and reliability-study evidence; separate mandatory criteria from studies.";
    }
    metadata def Recovery :> UseIntent {
        attribute :>> category = "Recovery";
        attribute :>> intendedUse = "Screen conditional recovery authority, exposure or energy for supplied capabilities and route.";
        attribute :>> domain = "Named configuration, current, orientation, usable reserve, approach and response assumptions.";
        attribute :>> excludedUses = "No demonstrated thrust, whole-river recoverability, physical independence, shore retention or pickup.";
        attribute :>> evidenceNeeded = "Measured installed propulsion/energy and casualty-response envelopes; route and approach evidence with uncertainty.";
    }
    metadata def Sailing :> UseIntent {
        attribute :>> category = "Sailing";
        attribute :>> intendedUse = "Estimate polar demand, conditional progress or hull/route screens under declared inputs.";
        attribute :>> domain = "Supplied polar/geometry, current, wind, leeway and bounded route assumptions.";
        attribute :>> excludedUses = "Demand ratios and solved states do not predict a measured voyage or establish performance outside the studied envelope.";
        attribute :>> evidenceNeeded = "Both-tack measured polar and mass/drag evidence; discretization, convergence and environment-domain sensitivity.";
    }
    metadata def Equipment :> UseIntent {
        attribute :>> category = "Equipment";
        attribute :>> intendedUse = "Account for candidate equipment allocations or illustrative actuator/energy loads.";
        attribute :>> domain = "Declared included/excluded components, duty assumptions, modes and accounting boundary.";
        attribute :>> excludedUses = "An allowance or arithmetic rollup is not a measured installed budget, peak capability or architecture downselect.";
        attribute :>> evidenceNeeded = "Identified component/BOM and synchronized mass, peak/average power, duty and environmental measurements.";
    }
    metadata def Encounter :> UseIntent {
        attribute :>> category = "Encounter";
        attribute :>> intendedUse = "Screen class detection, acquisition or response-distance/exposure from supplied bounds.";
        attribute :>> domain = "Specified target/class, timing, uncertainty, controller state and envelope assumptions.";
        attribute :>> excludedUses = "Allocated observation or response bounds are not demonstrated sensing coverage, maneuver completion or accepted safety margins.";
        attribute :>> evidenceNeeded = "Installed target-class detection/error/dropout and timing evidence including interacting faults and occupied maneuvers.";
    }
    metadata def Weather :> UseIntent {
        attribute :>> category = "Weather";
        attribute :>> intendedUse = "Explore environmental or passage-exposure sensitivity with declared scenario values.";
        attribute :>> domain = "Named wind/current/wave/weather assumptions, geometry and sampled domain.";
        attribute :>> excludedUses = "Scenario sweeps are not calibrated probability distributions, full-domain coverage or voyage reliability evidence.";
        attribute :>> evidenceNeeded = "Observed environmental basis, dependence and coverage review; uncertainty and sensitivity for the proposed use.";
    }
    metadata def EnergyReliability :> UseIntent {
        attribute :>> category = "EnergyReliability";
        attribute :>> intendedUse = "Evaluate conditional energy reconciliation or mission-reliability arithmetic for the named subject.";
        attribute :>> domain = "Declared load/exposure/storage boundaries or failure-rate partition, dependence and hazard assumptions.";
        attribute :>> excludedUses = "Numerical success does not establish measured load, accepted rates, independence or physical reliability/energy sufficiency.";
        attribute :>> evidenceNeeded = "Configuration-specific measurements, rate/profile justification, common-cause/dependence review and uncertainty assessment.";
    }
    metadata def Geometry :> UseIntent {
        attribute :>> category = "Geometry";
        attribute :>> intendedUse = "Inspect a geometric/course or analytic hydrostatic fixture.";
        attribute :>> domain = "Declared coordinate/geometry conventions and simplified analytic assumptions.";
        attribute :>> excludedUses = "A consistent fixture is not surveyed course truth, validated free-surface response or installed-vessel performance.";
        attribute :>> evidenceNeeded = "Independent coordinate/unit checks, geometry survey or hydrostatic comparison relevant to the proposed use.";
    }
    metadata use001 : Equipment about BlueDogAcousticEquipment::Budget;
    metadata use002 : Inputs about BlueDogAerodynamicPolicy::convergenceInputs;
    metadata use003 : Encounter about BlueDogAvoidanceFailures::EvaluateExposure;
    metadata use004 : EnergyReliability about BlueDogCandidateEnergy::Reconciliation;
    metadata use005 : Encounter about BlueDogClassDetection::Assessment;
    metadata use006 : Encounter about BlueDogClassDetection::Summary;
    metadata use007 : Inputs about BlueDogConceptCredibility::Inputs;
    metadata use008 : Inputs about BlueDogConceptCredibility::SensitivityInputs;
    metadata use009 : Readiness about BlueDogConfigurationManagement::AccountingReview;
    metadata use010 : Readiness about BlueDogConfigurationManagement::currentReview;
    metadata use011 : Inputs about BlueDogCoupledOperation::Inputs;
    metadata use012 : Inputs about BlueDogCoupledSizing::Inputs;
    metadata use013 : Inputs about BlueDogCoupledUncertainty::Inputs;
    metadata use014 : HistoricalReview about BlueDogCurrentSizing::nominalReview;
    metadata use015 : HistoricalReview about BlueDogCurrentSizing::constructionReview;
    metadata use016 : HistoricalReview about BlueDogCurrentSizing::aerodynamicReview;
    metadata use017 : HistoricalReview about BlueDogCurrentSizing::hydrodynamicReview;
    metadata use018 : HistoricalReview about BlueDogCurrentSizing::energyReview;
    metadata use019 : HistoricalReview about BlueDogCurrentSizing::combinedReview;
    metadata use020 : Encounter about BlueDogEncounterEnvelope::Envelope;
    metadata use021 : Encounter about BlueDogEncounterEnvelope::Summary;
    metadata use022 : Inputs about BlueDogEncounterFeasibility::Inputs;
    metadata use023 : Encounter about BlueDogEncounterReview::Acquisition;
    metadata use024 : EnergyReliability about BlueDogEnergy::SustainedOperation;
    metadata use025 : EnergyReliability about BlueDogEnergy::SustainedEnergyVerification::calculation;
    metadata use026 : Weather about BlueDogEnvironmentReview::FetchSensitivity;
    metadata use027 : Geometry about BlueDogHydrostatics::analyticExample;
    metadata use028 : Inputs about BlueDogIntegratedCandidate::Inputs;
    metadata use029 : Recovery about BlueDogIntegratedCandidate::RecoveryScreen;
    metadata use030 : Recovery about BlueDogIntegratedCandidate::IC01RecoveryIllustration;
    metadata use031 : Recovery about BlueDogIntegratedCandidate::IC01InvertedRecoveryIllustration;
    metadata use032 : Recovery about BlueDogIntegratedCandidate::IC01NoRecoveryAuthority;
    metadata use033 : Weather about BlueDogLocationTraffic::WindowAssessment;
    metadata use034 : Inputs about BlueDogManeuverDynamics::Defaults;
    metadata use035 : Inputs about BlueDogManeuverDynamics::StudyInputs;
    metadata use036 : Inputs about BlueDogMissionSimulation::Inputs;
    metadata use037 : Rules about BlueDogNavigationController::Policy;
    metadata use038 : Rules about BlueDogNavigationController::Candidate;
    metadata use039 : Rules about BlueDogNavigationController::Geometry;
    metadata use040 : Rules about BlueDogNavigationController::Context;
    metadata use041 : Inputs about BlueDogOperatingEnvironment::Inputs;
    metadata use042 : Weather about BlueDogPassageExposure::Contours;
    metadata use043 : HistoricalReview about BlueDogRecordedSizing::nominalReview;
    metadata use044 : HistoricalReview about BlueDogRecordedSizing::constructionReview;
    metadata use045 : HistoricalReview about BlueDogRecordedSizing::aerodynamicReview;
    metadata use046 : HistoricalReview about BlueDogRecordedSizing::hydrodynamicReview;
    metadata use047 : HistoricalReview about BlueDogRecordedSizing::energyReview;
    metadata use048 : HistoricalReview about BlueDogRecordedSizing::combinedReview;
    metadata use049 : Recovery about BlueDogRecoveryRisk::Sensitivity;
    metadata use050 : EnergyReliability about BlueDogReliability::CruiseReliability;
    metadata use051 : EnergyReliability about BlueDogReliability::VoyageReliabilityVerification::calculation;
    metadata use052 : EnergyReliability about BlueDogReliabilityExamples::gorgeAssessment;
    metadata use053 : Readiness about BlueDogSafety::SafetyReview;
    metadata use054 : Readiness about BlueDogSafety::SafetyReview::failureModes;
    metadata use055 : Readiness about BlueDogSafety::currentReview;
    metadata use056 : Trade about BlueDogSailTrade::TradeAssessment;
    metadata use057 : Trade about BlueDogSailTrade::tailAssessment;
    metadata use058 : Trade about BlueDogSailTrade::camberAssessment;
    metadata use059 : Trade about BlueDogSailTrade::softAssessment;
    metadata use060 : Trade about BlueDogSailTrade::buoyancyIllustration;
    metadata use061 : Sailing about BlueDogSailing::PolarDemandAndHullScreen;
    metadata use062 : Sailing about BlueDogSailing::PolarVoyageAssessment;
    metadata use063 : Sailing about BlueDogSailing::PolarVoyageAssessment::cruise;
    metadata use064 : Sailing about BlueDogSailing::SailingSensitivity;
    metadata use065 : Sailing about BlueDogSailingExamples::upstreamBeat;
    metadata use066 : Sailing about BlueDogSailingExamples::upstreamRun;
    metadata use067 : Sailing about BlueDogSailingExamples::downstreamBeat;
    metadata use068 : Sailing about BlueDogSailingExamples::downstreamRun;
    metadata use069 : Sailing about BlueDogSailingExamples::westerlyPassage;
    metadata use070 : Sailing about BlueDogSailingExamples::easterlyPassage;
    metadata use071 : Sailing about BlueDogSailingExamples::lightWindDemand;
    metadata use072 : Sailing about BlueDogSailingExamples::strongWindDemand;
    metadata use073 : Sailing about BlueDogSailingExamples::highWindDemand;
    metadata use074 : Sailing about BlueDogSailingExamples::sensitivity;
    metadata use075 : Sailing about BlueDogSailingExamples::oceanDemand;
    metadata use076 : HistoricalReview about BlueDogSizingEvidence::Review;
    metadata use077 : Inputs about BlueDogStructuralBasis::Inputs;
    metadata use078 : Inputs about BlueDogStructure::MaterialInputs;
    metadata use079 : Inputs about BlueDogStructure::material;
    metadata use080 : Inputs about BlueDogSurfaceEnvironment::Inputs;
    metadata use081 : Inputs about BlueDogWavePerformance::Inputs;
    metadata use082 : Inputs about BlueDogWeather::Inputs;
    metadata use083 : Weather about BlueDogWeather::RegimeSensitivity;
    metadata use084 : Weather about BlueDogWeather::primary;
    metadata use085 : Weather about BlueDogWeather::construction;
    metadata use086 : Weather about BlueDogWeather::aerodynamic;
    metadata use087 : Weather about BlueDogWeather::hydrodynamic;
    metadata use088 : Weather about BlueDogWeather::energy;
    metadata use089 : Weather about BlueDogWeather::combined;
    metadata use090 : Equipment about BlueDogWindEquipment::Rollup;
    metadata use091 : Equipment about BlueDogWingActuator::accountingExample;
    metadata use092 : Inputs about BlueDogWingHeel::sweepInputs;
    metadata use093 : Rules about InlandExtended::General;
    metadata use094 : Rules about InlandExtended::ChannelsAndTSS;
    metadata use095 : Rules about InlandExtended::RestrictedVisibility;
    metadata use096 : Rules about InlandExtended::LightsAndShapes;
    metadata use097 : Rules about InlandExtended::Signals;
    metadata use098 : Rules about InlandExtended::LightFixture;
    metadata use099 : Rules about InlandExtended::Installation;
    metadata use100 : Rules about InlandExtended::SoundAppliance;
    metadata use101 : Rules about InlandExtended::ExemptionsAndSpecialCases;
    metadata use102 : Rules about InlandExtended::CandidateAssessment;
    metadata use103 : Rules about InlandExtended::SnapshotConsistency;
    metadata use104 : Rules about InlandExtended::SpecialDisplays;
    metadata use105 : Rules about InlandExtended::PassageProtocol;
    metadata use106 : Rules about InlandExtended::DistressCatalog;
    metadata use107 : Rules about InlandNavigationExperiment::Assess;
    metadata use108 : Equipment about MarineEnergy::BudgetRollup;
    metadata use109 : Recovery about RecoveryPropulsionTrade::RecoverySizing;
    metadata use110 : Geometry about TransGorgeCourse::GateGeometry;

    calc def UsePreconditions {
        doc /* Supplied review assertions for a proposed use, not an acceptance decision or a requirement that the design pass its screens. */
        in intendedUseReviewed : Boolean [1];
        in configurationApplicable : Boolean [1];
        in domainApplicable : Boolean [1];
        in inputPedigreeReviewed : Boolean [1];
        in implementationVerified : Boolean [1];
        in validationAdequateForUse : Boolean [1];
        in uncertaintyReported : Boolean [1];
        in sensitivityReviewed : Boolean [1];
        in defectsDispositioned : Boolean [1];
        in limitationsReported : Boolean [1];
        return eligible : Boolean = intendedUseReviewed and configurationApplicable and domainApplicable and inputPedigreeReviewed and implementationVerified and validationAdequateForUse and uncertaintyReported and sensitivityReviewed and defectsDispositioned and limitationsReported;
    }
}

package BlueDogRisks {
    private import ScalarValues::*;
    doc /* Technical risk assessment for the next concept-selection and integrated-test
     * planning spiral. Qualitative likelihood rates the prospect that an identified
     * limitation forces redesign or operating-envelope restriction. Consequence rates
     * the credible effect if it is not addressed. These are ordinal engineering
     * judgments, not incident probabilities, expected losses or residual-risk acceptance.
     * Standard technicalRisk probability and impact remain unset without quantitative evidence.
     */
    metadata def Tracking :> RiskMetadata::Risk {
        attribute identifier : String;
        attribute riskKind : String;
        attribute statement : String;
        attribute consequence : String;
        attribute uncertainty : String;
        attribute priority : String;
        attribute priorityRationale : String;
        attribute reductionAction : String;
        attribute closureEvidence : String;
        attribute likelihoodClass : String default "";
        attribute consequenceClass : String default "";
        attribute confidence : String default "Unassessed";
        attribute assessedOn : String default "2026-10-15";
        attribute assessor : String default "Analysis agent; owner review pending";
        attribute assessmentScope : String default "Next concept-selection and integrated-test planning spiral; likelihood of redesign or operating-envelope restriction, not a probability of an accident on a voyage.";
        attribute assessmentBasis : String default "Unassessed";
        attribute evidenceReference : String default "None accepted";
        attribute residualDisposition : String default "Open; no residual-risk acceptance recorded";
    }
    part traffic {
        metadata workStatus : ModelingMetadata::StatusInfo { status = ModelingMetadata::StatusKind::open; owner = "Analysis agent; owner reviews disposition"; }
        metadata risk : Tracking {
            riskKind = "technical";
            identifier = "R-001";
            likelihoodClass = "Likely";
            consequenceClass = "Critical";
            confidence = "Low";
            assessmentBasis = "Current class-specific detection allocations require reviewed kinematics, consequence-informed clearance, observation and whole-response reliability, confidence and risk disposition. Those inputs and installed evidence remain open. Historical IC-01 synthetic closure used a uniform 750 m sensing hypothesis; it does not establish the new class policy or measured installation. A missed encounter can compromise other river users.";
            evidenceReference = "models/analyses/class-specific-detection.sysml; models/analyses/encounter-review.sysml (historical); models/analyses/integrated-candidate.sysml (historical sensing hypothesis); models/vehicle/requirements.sysml";
            residualDisposition = "Open; Mitigate; require sensing and maneuver evidence before admitting the affected operating envelope. No residual-risk acceptance recorded.";
            statement = "If installed sensing cannot acquire and track relevant traffic early enough, the vessel cannot safely execute the allocated avoidance maneuver.";
            consequence = "Collision or impediment of other river users, especially in darkness or spray.";
            uncertainty = "No installed class-specific detection envelope, consequence review or correlated maneuver-response evidence establishes an accepted current allocation.";
            priority = "Now: safety feasibility";
            priorityRationale = "Safety consequence and potential architecture blocker; a desktop envelope study can expose infeasibility before equipment selection.";
            reductionAction = "Analyze detection geometry, target visibility, latency and maneuver sensitivity together; define a shore-camera and controlled-target experiment before selecting equipment.";
            closureEvidence = "A candidate sensing/maneuver architecture has a bounded operating envelope supported by independent observations; unmet cases have explicit restrictions or a revised architecture.";
        }
    }
    dependency trafficTrace0 from traffic to BlueDogEncounterReview::criteria {
        doc /* Historical six-class allocation study; current allocation is traced separately. */
    }
    dependency trafficCurrentPolicy from traffic to BlueDogClassDetection::policy;
    dependency trafficLocationReview from traffic to BlueDogLocationTraffic::policy;
    dependency trafficTrace1 from traffic to BlueDogDFMEA::starter::trafficMiss;
    dependency trafficTrace2 from traffic to BlueDogRequirements::trafficSafety;
    part recovery {
        metadata workStatus : ModelingMetadata::StatusInfo { status = ModelingMetadata::StatusKind::open; owner = "Analysis agent; owner reviews disposition"; }
        metadata risk : Tracking {
            riskKind = "technical";
            identifier = "R-002";
            likelihoodClass = "Likely";
            consequenceClass = "Critical";
            confidence = "Medium";
            assessmentBasis = "IC-01 reaches synthetic approaches in six casualty/end-of-exposure cases using allocated independent power, control, observations and upright/inverted thrust. Shared-power and empty-bank controls still reach shore contact. No surveyed casualty coverage, measured fault isolation, finite-turn recovery dynamics or retention is established. Site, propulsion or operating restrictions remain likely; unresolved loss of recovery can expose other traffic.";
            evidenceReference = "models/analyses/recovery-site-review.sysml; tests/test_course_recovery.py; evidence/runs/2026-10-15-integrated-candidate/integrated-mission.json; models/analyses/recovery-risk.sysml";
            residualDisposition = "Open; Mitigate; retain casualty restrictions until site coverage and installed recovery authority are demonstrated. No residual-risk acceptance recorded.";
            statement = "If a casualty removes sensing, steering or buoyancy, autonomous shore recovery may fail before another traffic encounter.";
            consequence = "Collision, stranded vessel or unrecovered debris.";
            uncertainty = "Reachability and common-cause exposure are unvalidated; low failure probability is not established.";
            priority = "Now: safety feasibility";
            priorityRationale = "Safety consequence; shares maneuver and sensing assumptions with R-001, so investigate those dependencies together.";
            reductionAction = "Exercise coupled loss-of-sensing, steering, power and capsize cases against reachable shore sites; identify the measurements needed for a controlled recovery trial.";
            closureEvidence = "Reachable recovery coverage is demonstrated for declared casualty cases; unsupported cases are excluded or mitigated and residual safety risk is explicitly reviewed.";
        }
    }
    dependency recoveryTrace0 from recovery to BlueDogRecoveryRisk::Sensitivity;
    dependency recoveryTrace1 from recovery to BlueDogDFMEA::starter::steeringJam;
    dependency recoveryTrace2 from recovery to BlueDogDFMEA::starter::powerCommonCause;
    dependency recoveryTrace3 from recovery to BlueDogDesignDecisions::recoveryScope;
    dependency recoveryTrace4 from recovery to GorgeChallenge::casualtyFlotation;
    part structure {
        metadata workStatus : ModelingMetadata::StatusInfo { status = ModelingMetadata::StatusKind::open; owner = "Analysis agent; owner reviews disposition"; }
        metadata risk : Tracking {
            riskKind = "technical";
            identifier = "R-003";
            likelihoodClass = "Possible";
            consequenceClass = "Critical";
            confidence = "Low";
            assessmentBasis = "The structural basis explicitly marks 10 GPa and 50 MPa as unqualified and lacks joint/load correlation. There is insufficient evidence to call the candidate inadequate or robust, so redesign is possible rather than presumed likely. Loss of a keel or hull load path can defeat flotation and recovery.";
            evidenceReference = "models/analyses/structural-basis.sysml; models/vehicle/verification.sysml";
            residualDisposition = "Open; Mitigate; obtain production material and attachment evidence and rerun affected sizing before structural reliance. No residual-risk acceptance recorded.";
            statement = "If wet laminate, joint or load assumptions are optimistic, the proposed structure may be too heavy or may lose its load path in service.";
            consequence = "Structural failure, loss of recovery capability or invalid sizing frontier.";
            uncertainty = "10 GPa and 50 MPa are unqualified; joint, fatigue and functional deformation evidence is missing.";
            priority = "Next: sizing credibility";
            priorityRationale = "Affects mass, buoyancy and recovery across every concept; sensitivity work can focus inexpensive experiments.";
            reductionAction = "Sweep material and joint/load assumptions to rank sensitivity; specify production coupons and attachment tests around the assumptions that change design selection.";
            closureEvidence = "Credited properties and applicable loads are supported within a declared scope; re-sizing establishes margins or identifies the required redesign.";
        }
    }
    dependency structureTrace0 from structure to BlueDogStructuralBasis::Inputs;
    dependency structureTrace1 from structure to BlueDogStructure::structuralIntegrity;
    dependency structureTrace2 from structure to BlueDogRequirementVerification::StructuralMaterialEvidence;
    dependency structureTrace3 from structure to BlueDogRequirementVerification::StructuralLoadEvidence;
    dependency structureTrace4 from structure to BlueDogDFMEA::starter::hullLeak;
    dependency structureTrace5 from structure to BlueDogDFMEA::starter::keelLoss;
    part wing {
        metadata workStatus : ModelingMetadata::StatusInfo { status = ModelingMetadata::StatusKind::open; owner = "Analysis agent; owner reviews disposition"; }
        metadata risk : Tracking {
            riskKind = "technical";
            identifier = "R-004";
            likelihoodClass = "Likely";
            consequenceClass = "Critical";
            confidence = "Medium";
            assessmentBasis = "Recorded mesh and heel sensitivities motivate restricted incidence and conservative force/moment allowances. Both-tack and off-design measurements and loaded drive behavior remain absent. Rig or actuator changes are likely; an overloaded or jammed actuator can remove control authority, so the credible consequence is safety-critical even though a physical failure rate is unknown.";
            evidenceReference = "models/analyses/aerodynamic-policy.sysml; docs/sail-trade.md; evidence/runs/2026-10-13-surface-environment/summary.json";
            residualDisposition = "Open; Mitigate; keep rig selection open and bound forces, moments and drive demand with measurements. No residual-risk acceptance recorded.";
            statement = "If the wing force or trim-moment model is optimistic, the selected rig may lack progress or overload its actuator.";
            consequence = "Mission noncompletion, excess energy demand or loss of control.";
            uncertainty = "No measured both-tack polar; stall, broadside response and loaded gearbox behavior remain uncertain.";
            priority = "Next: sizing credibility";
            priorityRationale = "High leverage on rig selection, energy and vessel size; avoid refining geometry inside an unsupported aerodynamic assumption.";
            reductionAction = "Rank force and moment sensitivity at mission-critical conditions; define force/moment and drive-energy component tests supporting the first IC-01-scale build.";
            closureEvidence = "Independent measurements bound the model at conditions used for concept selection; force, trim and failure behavior support the chosen rig or trigger a new trade.";
        }
    }
    dependency wingTrace0 from wing to BlueDogDesignDecisions::aerodynamicScope;
    dependency wingTrace1 from wing to BlueDogDesignDecisions::holdingDrive;
    dependency wingTrace2 from wing to BlueDogRequirements::cruiseEvidence;
    dependency wingTrace3 from wing to BlueDogDFMEA::starter::sailJam;
    part energy {
        metadata workStatus : ModelingMetadata::StatusInfo { status = ModelingMetadata::StatusKind::open; owner = "Analysis agent; owner reviews disposition"; }
        metadata risk : Tracking {
            riskKind = "technical";
            identifier = "R-005";
            likelihoodClass = "Likely";
            consequenceClass = "Critical";
            confidence = "Medium";
            assessmentBasis = "IC-01 has 102.062 Wh main-pack headroom against 833.938 Wh nominal allocated demand and separately budgets recovery standby and propulsion. Its additional 8 W sensing demand, equipment mass, usable capacity, duty and isolation remain unmeasured. This is a conditional allocation, not installed energy evidence. Energy or operating allocations remain likely to need adjustment; exhausted or shared power can remove safety and recovery functions.";
            evidenceReference = "models/analyses/integrated-candidate.sysml; evidence/runs/2026-10-15-integrated-candidate/integrated-sizing.json; evidence/runs/2026-10-15-integrated-candidate/integrated-mission.json";
            residualDisposition = "Open; Mitigate; establish measured capacity/load bounds and protect independent recovery authority before relying on the margin. No residual-risk acceptance recorded.";
            statement = "If installed loads, battery capacity or correlated duty cycles exceed assumptions, the vessel may exhaust usable energy before passage or recovery completes.";
            consequence = "Abort or loss of safety and recovery functions.";
            uncertainty = "IC-01 has nominal allocated margin; installed sensing demand, usable capacity, duty and independent recovery loads are unmeasured.";
            priority = "Next: integration credibility";
            priorityRationale = "Simultaneous sensing performance, installed demand and power isolation can overturn the allocated concept despite virtual closure.";
            reductionAction = "Propagate correlated load and capacity uncertainty through chronological passage and abort cases; specify measured-load replay on the electrical bench.";
            closureEvidence = "Evidence-backed usable energy and load profiles support passage and recovery margins in the declared scenario set; protection and common-cause faults have explicit dispositions.";
        }
    }
    dependency energyTrace0 from energy to BlueDogDesignDecisions::energyEvidenceAcceptance;
    dependency energyTrace1 from energy to BlueDogDFMEA::starter::batteryFault;
    dependency energyTrace2 from energy to BlueDogDFMEA::starter::powerCommonCause;
    dependency energyTrace3 from energy to BlueDogRequirements::sustainedReserveProtection;
    part mission {
        metadata workStatus : ModelingMetadata::StatusInfo { status = ModelingMetadata::StatusKind::open; owner = "Analysis agent; owner reviews disposition"; }
        metadata risk : Tracking {
            riskKind = "technical";
            identifier = "R-006";
            likelihoodClass = "Demonstrated";
            consequenceClass = "Major";
            confidence = "High";
            assessmentBasis = "IC-01 closes a bounded synthetic reach with averaged-tack sailing and point-mass recovery. It does not establish complete Gorge, wave or physical maneuver coverage. All four archived wave-performance mission replays stop outside their supported domain at departure despite 32 small-wave operating cases. Synthetic traffic and weather limit transfer; greater sample count alone cannot establish the operating envelope.";
            evidenceReference = "evidence/runs/2026-10-15-integrated-candidate/integrated-mission.json; evidence/runs/2026-10-13-wave-performance/summary.json; docs/mission-simulation.md";
            residualDisposition = "Open; Restrict claims to supported domains; expand and correlate decision-driving coverage before comparing mission success. No residual-risk acceptance recorded.";
            statement = "If weather, traffic or physics coverage is unrepresentative, the optimizer may select a boat whose apparent mission success does not transfer to the river.";
            consequence = "Wrong concept selection or unjustified operating envelope.";
            uncertainty = "Synthetic scenario fractions are not calibrated real-world mission probabilities.";
            priority = "Continuous: decision credibility";
            priorityRationale = "Cross-cutting dependency of every ranking; maintain alongside focused investigations rather than treating more Monte Carlo runs as validation.";
            reductionAction = "Track scenario coverage and model validity; compare candidates using common seeded realizations, explicit edge cases and sensitivity to uncertain inputs.";
            closureEvidence = "Decision-driving scenarios and model domains have documented evidence and limitations; conclusions remain stable or the unresolved sensitivity is carried into the review.";
        }
    }
    dependency missionTrace0 from mission to BlueDogDesignDecisions::uncertaintyPolicy;
    dependency missionTrace1 from mission to BlueDogRequirements::missionReliability;
    dependency missionTrace2 from mission to FailureAnalysis::DesignFailureReview;
}

package BlueDogDFMEA {
    private import ScalarValues::*;
    doc /* Initial design failure-mode review. Rows are hypotheses, not exhaustive
     * hazard coverage or measured rates. No ordinal score is converted to probability.
     * Scope includes sailing, holds, recovery, and common-cause failures.
     */
    private import FailureAnalysis::*;
    part starter : Review {
        ref part :>> system = BlueDog::Architecture::missionContext.boat;
        attribute :>> scopeReviewed default = false;
        part hullLeak : ReviewRow subsets modes {
            ref part :>> affected = BlueDog::Architecture::missionContext.boat.hullAndRig.printedHull;
            attribute :>> identifier = "FM-001";
            attribute :>> intendedFunction = "Retain buoyancy";
            occurrence failureModeEvent : FailureAnalysis::Event { attribute :>> description = "Printed seam leaks"; }
            ref occurrence :>> failureMode = failureModeEvent;
            occurrence causeEvent : FailureAnalysis::Event { attribute :>> description = "Cyclic wave load or print defect"; }
            ref occurrence :>> cause = causeEvent;
            occurrence localEffectEvent : FailureAnalysis::Event { attribute :>> description = "Water enters hull"; }
            ref occurrence :>> localEffect = localEffectEvent;
            occurrence missionEffectEvent : FailureAnalysis::Event { attribute :>> description = "Buoyancy or electrical function lost"; }
            ref occurrence :>> missionEffect = missionEffectEvent;
            attribute :>> proposedDetection = "Ingress sensing; acceptance unproven";
            attribute :>> recommendedAction = "Coupon fatigue, seam pressure test and flooded-compartment trial";
            attribute :>> ownerRole = "Hull/structure";
            attribute :>> safetyCritical = true;
            metadata workStatus : ModelingMetadata::StatusInfo { status = ModelingMetadata::StatusKind::open; }
            metadata risk : RiskMetadata::Risk;
        }
        part keelLoss : ReviewRow subsets modes {
            ref part :>> affected = BlueDog::Architecture::missionContext.boat.hullAndRig.keelAndBallast;
            attribute :>> identifier = "FM-002";
            attribute :>> intendedFunction = "Maintain righting moment";
            occurrence failureModeEvent : FailureAnalysis::Event { attribute :>> description = "Keel attachment fractures"; }
            ref occurrence :>> failureMode = failureModeEvent;
            occurrence causeEvent : FailureAnalysis::Event { attribute :>> description = "Fatigue or impact"; }
            ref occurrence :>> cause = causeEvent;
            occurrence localEffectEvent : FailureAnalysis::Event { attribute :>> description = "Ballast detached"; }
            ref occurrence :>> localEffect = localEffectEvent;
            occurrence missionEffectEvent : FailureAnalysis::Event { attribute :>> description = "Persistent inversion or vessel loss"; }
            ref occurrence :>> missionEffect = missionEffectEvent;
            attribute :>> proposedDetection = "Attitude sensor; attachment inspection";
            attribute :>> recommendedAction = "Proof load and fatigue qualification of joint";
            attribute :>> ownerRole = "Hull/structure";
            attribute :>> safetyCritical = true;
            metadata workStatus : ModelingMetadata::StatusInfo { status = ModelingMetadata::StatusKind::open; }
            metadata risk : RiskMetadata::Risk;
        }
        part steeringJam : ReviewRow subsets modes {
            ref part :>> affected = BlueDog::Architecture::missionContext.boat.actuation;
            attribute :>> identifier = "FM-003";
            attribute :>> intendedFunction = "Control heading";
            occurrence failureModeEvent : FailureAnalysis::Event { attribute :>> description = "Rudder or linkage jams"; }
            ref occurrence :>> failureMode = failureModeEvent;
            occurrence causeEvent : FailureAnalysis::Event { attribute :>> description = "Milfoil wrap, debris or actuator fault"; }
            ref occurrence :>> cause = causeEvent;
            occurrence localEffectEvent : FailureAnalysis::Event { attribute :>> description = "Commanded rudder motion unavailable"; }
            ref occurrence :>> localEffect = localEffectEvent;
            occurrence missionEffectEvent : FailureAnalysis::Event { attribute :>> description = "Reduced VMG; boundary excursion or collision"; }
            ref occurrence :>> missionEffect = missionEffectEvent;
            attribute :>> proposedDetection = "Position/current disagreement detection to be designed";
            attribute :>> recommendedAction = "Weed-jam injection and autonomous clearing trial";
            attribute :>> ownerRole = "Actuation";
            attribute :>> safetyCritical = true;
            metadata workStatus : ModelingMetadata::StatusInfo { status = ModelingMetadata::StatusKind::open; }
            metadata risk : RiskMetadata::Risk;
        }
        part sailJam : ReviewRow subsets modes {
            ref part :>> affected = BlueDog::Architecture::missionContext.boat.actuation;
            attribute :>> identifier = "FM-004";
            attribute :>> intendedFunction = "Control sail force";
            occurrence failureModeEvent : FailureAnalysis::Event { attribute :>> description = "Wing trim jams"; }
            ref occurrence :>> failureMode = failureModeEvent;
            occurrence causeEvent : FailureAnalysis::Event { attribute :>> description = "Bearing wear, salt or drive failure"; }
            ref occurrence :>> cause = causeEvent;
            occurrence localEffectEvent : FailureAnalysis::Event { attribute :>> description = "Trim fixed in unsafe position"; }
            ref occurrence :>> localEffect = localEffectEvent;
            occurrence missionEffectEvent : FailureAnalysis::Event { attribute :>> description = "VMG loss or overpower/capsize"; }
            ref occurrence :>> missionEffect = missionEffectEvent;
            attribute :>> proposedDetection = "Command/response monitoring to be designed";
            attribute :>> recommendedAction = "Jam test at adverse trim; passive load limiting trade";
            attribute :>> ownerRole = "Actuation";
            attribute :>> safetyCritical = true;
            metadata workStatus : ModelingMetadata::StatusInfo { status = ModelingMetadata::StatusKind::open; }
            metadata risk : RiskMetadata::Risk;
        }
        part batteryFault : ReviewRow subsets modes {
            ref part :>> affected = BlueDog::Architecture::missionContext.boat.energy.storage;
            attribute :>> identifier = "FM-005";
            attribute :>> intendedFunction = "Supply essential power";
            occurrence failureModeEvent : FailureAnalysis::Event { attribute :>> description = "Battery disconnects or faults"; }
            ref occurrence :>> failureMode = failureModeEvent;
            occurrence causeEvent : FailureAnalysis::Event { attribute :>> description = "Cell degradation, BMS trip or short"; }
            ref occurrence :>> cause = causeEvent;
            occurrence localEffectEvent : FailureAnalysis::Event { attribute :>> description = "Bus power lost or overheating"; }
            ref occurrence :>> localEffect = localEffectEvent;
            occurrence missionEffectEvent : FailureAnalysis::Event { attribute :>> description = "Mission loss; possible thermal damage"; }
            ref occurrence :>> missionEffect = missionEffectEvent;
            attribute :>> proposedDetection = "Voltage/temperature/current sensing to be verified";
            attribute :>> recommendedAction = "Cold/aged-cell loading and BMS fault injection";
            attribute :>> ownerRole = "Power";
            attribute :>> safetyCritical = true;
            metadata workStatus : ModelingMetadata::StatusInfo { status = ModelingMetadata::StatusKind::open; }
            metadata risk : RiskMetadata::Risk;
        }
        part harvestLoss : ReviewRow subsets modes {
            ref part :>> affected = BlueDog::Architecture::missionContext.boat.energy.harvesting;
            attribute :>> identifier = "FM-006";
            attribute :>> intendedFunction = "Replenish stored energy";
            occurrence failureModeEvent : FailureAnalysis::Event { attribute :>> description = "Harvesting stops"; }
            ref occurrence :>> failureMode = failureModeEvent;
            occurrence causeEvent : FailureAnalysis::Event { attribute :>> description = "Connector corrosion or panel damage"; }
            ref occurrence :>> cause = causeEvent;
            occurrence localEffectEvent : FailureAnalysis::Event { attribute :>> description = "Persistent energy deficit"; }
            ref occurrence :>> localEffect = localEffectEvent;
            occurrence missionEffectEvent : FailureAnalysis::Event { attribute :>> description = "Long-hold exposure exhausts reserve"; }
            ref occurrence :>> missionEffect = missionEffectEvent;
            attribute :>> proposedDetection = "Harvest-current residual monitoring to be designed";
            attribute :>> recommendedAction = "No-harvest fault campaign and reserve policy validation";
            attribute :>> ownerRole = "Power";
            attribute :>> safetyCritical = false;
            metadata workStatus : ModelingMetadata::StatusInfo { status = ModelingMetadata::StatusKind::open; }
            metadata risk : RiskMetadata::Risk;
        }
        part powerCommonCause : ReviewRow subsets modes {
            ref part :>> affected = BlueDog::Architecture::missionContext.boat.energy.powerManagement;
            attribute :>> identifier = "FM-007";
            attribute :>> intendedFunction = "Keep essential services powered";
            occurrence failureModeEvent : FailureAnalysis::Event { attribute :>> description = "Shared bus fault disables multiple functions"; }
            ref occurrence :>> failureMode = failureModeEvent;
            occurrence causeEvent : FailureAnalysis::Event { attribute :>> description = "Regulator short or common water ingress"; }
            ref occurrence :>> cause = causeEvent;
            occurrence localEffectEvent : FailureAnalysis::Event { attribute :>> description = "Navigation, actuation and telemetry lost together"; }
            ref occurrence :>> localEffect = localEffectEvent;
            occurrence missionEffectEvent : FailureAnalysis::Event { attribute :>> description = "Mission and observation lost"; }
            ref occurrence :>> missionEffect = missionEffectEvent;
            attribute :>> proposedDetection = "Independent health path not yet designed";
            attribute :>> recommendedAction = "Assess isolation and independence; common-cause fault injection";
            attribute :>> ownerRole = "Power/system";
            attribute :>> safetyCritical = true;
            metadata workStatus : ModelingMetadata::StatusInfo { status = ModelingMetadata::StatusKind::open; }
            metadata risk : RiskMetadata::Risk;
        }
        part navigationFault : ReviewRow subsets modes {
            ref part :>> affected = BlueDog::Architecture::missionContext.boat.navigation.positionAndAttitude;
            attribute :>> identifier = "FM-008";
            attribute :>> intendedFunction = "Estimate position and heading";
            occurrence failureModeEvent : FailureAnalysis::Event { attribute :>> description = "Plausible wrong navigation solution"; }
            ref occurrence :>> failureMode = failureModeEvent;
            occurrence causeEvent : FailureAnalysis::Event { attribute :>> description = "Bias, stale data or corrupted input"; }
            ref occurrence :>> cause = causeEvent;
            occurrence localEffectEvent : FailureAnalysis::Event { attribute :>> description = "Guidance uses wrong state"; }
            ref occurrence :>> localEffect = localEffectEvent;
            occurrence missionEffectEvent : FailureAnalysis::Event { attribute :>> description = "Boundary/traffic hazard and route failure"; }
            ref occurrence :>> missionEffect = missionEffectEvent;
            attribute :>> proposedDetection = "Plausibility checks; independent reference unresolved";
            attribute :>> recommendedAction = "Biased/stale-sensor injection across speed/current profiles";
            attribute :>> ownerRole = "Navigation";
            attribute :>> safetyCritical = true;
            metadata workStatus : ModelingMetadata::StatusInfo { status = ModelingMetadata::StatusKind::open; }
            metadata risk : RiskMetadata::Risk;
        }
        part controlLockup : ReviewRow subsets modes {
            ref part :>> affected = BlueDog::Architecture::missionContext.boat.control.missionManager;
            attribute :>> identifier = "FM-009";
            attribute :>> intendedFunction = "Execute autonomous mission";
            occurrence failureModeEvent : FailureAnalysis::Event { attribute :>> description = "Controller hangs or repeats invalid command"; }
            ref occurrence :>> failureMode = failureModeEvent;
            occurrence causeEvent : FailureAnalysis::Event { attribute :>> description = "Systematic software fault or reset corruption"; }
            ref occurrence :>> cause = causeEvent;
            occurrence localEffectEvent : FailureAnalysis::Event { attribute :>> description = "Mission logic stops or is unsafe"; }
            ref occurrence :>> localEffect = localEffectEvent;
            occurrence missionEffectEvent : FailureAnalysis::Event { attribute :>> description = "No progress or unsafe actuation"; }
            ref occurrence :>> missionEffect = missionEffectEvent;
            attribute :>> proposedDetection = "Watchdog and restoration requirements; unverified";
            attribute :>> recommendedAction = "Fault injection and persisted-state consistency testing";
            attribute :>> ownerRole = "Autonomy";
            attribute :>> safetyCritical = true;
            metadata workStatus : ModelingMetadata::StatusInfo { status = ModelingMetadata::StatusKind::open; }
            metadata risk : RiskMetadata::Risk;
        }
        part trafficMiss : ReviewRow subsets modes {
            ref part :>> affected = BlueDog::Architecture::missionContext.boat.control.collisionAvoidance;
            attribute :>> identifier = "FM-010";
            attribute :>> intendedFunction = "Avoid other vessels";
            occurrence failureModeEvent : FailureAnalysis::Event { attribute :>> description = "Traffic conflict missed"; }
            ref occurrence :>> failureMode = failureModeEvent;
            occurrence causeEvent : FailureAnalysis::Event { attribute :>> description = "Sensor blind spot or prediction error"; }
            ref occurrence :>> cause = causeEvent;
            occurrence localEffectEvent : FailureAnalysis::Event { attribute :>> description = "The required encounter response is unavailable or too late"; }
            ref occurrence :>> localEffect = localEffectEvent;
            occurrence missionEffectEvent : FailureAnalysis::Event { attribute :>> description = "Collision risk"; }
            ref occurrence :>> missionEffect = missionEffectEvent;
            attribute :>> proposedDetection = "Independent lookout unavailable onboard";
            attribute :>> recommendedAction = "Non-AIS traffic scenarios and safe boundary strategies";
            attribute :>> ownerRole = "Autonomy/safety";
            attribute :>> safetyCritical = true;
            metadata workStatus : ModelingMetadata::StatusInfo { status = ModelingMetadata::StatusKind::open; }
            metadata risk : RiskMetadata::Risk;
        }
        part radioLoss : ReviewRow subsets modes {
            ref part :>> affected = BlueDog::Architecture::missionContext.boat.communications.telemetryRadio;
            attribute :>> identifier = "FM-011";
            attribute :>> intendedFunction = "Provide live observation";
            occurrence failureModeEvent : FailureAnalysis::Event { attribute :>> description = "Radio link unavailable"; }
            ref occurrence :>> failureMode = failureModeEvent;
            occurrence causeEvent : FailureAnalysis::Event { attribute :>> description = "Antenna wetting, shadowing or radio fault"; }
            ref occurrence :>> cause = causeEvent;
            occurrence localEffectEvent : FailureAnalysis::Event { attribute :>> description = "Live data cannot reach shore"; }
            ref occurrence :>> localEffect = localEffectEvent;
            occurrence missionEffectEvent : FailureAnalysis::Event { attribute :>> description = "Observation outage; autonomy must continue"; }
            ref occurrence :>> missionEffect = missionEffectEvent;
            attribute :>> proposedDetection = "Contact-age monitoring and retained logs";
            attribute :>> recommendedAction = "Wet/inverted antenna trials and 24-hour outage/reconnect test";
            attribute :>> ownerRole = "Communications";
            attribute :>> safetyCritical = false;
            metadata workStatus : ModelingMetadata::StatusInfo { status = ModelingMetadata::StatusKind::open; }
            metadata risk : RiskMetadata::Risk;
        }
        part motorUncommanded : ReviewRow subsets modes {
            ref part :>> affected = BlueDog::Architecture::missionContext.boat.recovery.motorSystem;
            attribute :>> identifier = "FM-012";
            attribute :>> intendedFunction = "Provide controlled recovery thrust";
            occurrence failureModeEvent : FailureAnalysis::Event { attribute :>> description = "Motor energizes during qualifying sailing"; }
            ref occurrence :>> failureMode = failureModeEvent;
            occurrence causeEvent : FailureAnalysis::Event { attribute :>> description = "Driver short or command gating fault"; }
            ref occurrence :>> cause = causeEvent;
            occurrence localEffectEvent : FailureAnalysis::Event { attribute :>> description = "Unintended powered propulsion"; }
            ref occurrence :>> localEffect = localEffectEvent;
            occurrence missionEffectEvent : FailureAnalysis::Event { attribute :>> description = "Challenge disqualification or contact hazard"; }
            ref occurrence :>> missionEffect = missionEffectEvent;
            attribute :>> proposedDetection = "Isolation and qualification latch; unverified";
            attribute :>> recommendedAction = "Stuck-driver test and independent propulsion isolation";
            attribute :>> ownerRole = "Recovery";
            attribute :>> safetyCritical = true;
            metadata workStatus : ModelingMetadata::StatusInfo { status = ModelingMetadata::StatusKind::open; }
            metadata risk : RiskMetadata::Risk;
        }
        part recoveryCaptureFault : ReviewRow subsets modes {
            ref part :>> affected = BlueDog::Architecture::missionContext.boat.hullAndRig.handling;
            attribute :>> identifier = "FM-013";
            attribute :>> intendedFunction = "Retain and retrieve the vessel safely";
            occurrence failureModeEvent : FailureAnalysis::Event { attribute :>> description = "Recovery approach cannot be captured or retained"; }
            ref occurrence :>> failureMode = failureModeEvent;
            occurrence causeEvent : FailureAnalysis::Event { attribute :>> description = "Unsuitable shore geometry, waves or incompatible handling interface"; }
            ref occurrence :>> cause = causeEvent;
            occurrence localEffectEvent : FailureAnalysis::Event { attribute :>> description = "Vessel escapes or requires an unsafe manual reach"; }
            ref occurrence :>> localEffect = localEffectEvent;
            occurrence missionEffectEvent : FailureAnalysis::Event { attribute :>> description = "Operator exposure and loss of recoverable vessel"; }
            ref occurrence :>> missionEffect = missionEffectEvent;
            attribute :>> proposedDetection = "Surveyed approach and independent capture/retention observation; unverified";
            attribute :>> recommendedAction = "Test approach, capture, retention and one-person pickup under admitted conditions";
            attribute :>> ownerRole = "Owner/handling";
            attribute :>> safetyCritical = true;
            metadata workStatus : ModelingMetadata::StatusInfo { status = ModelingMetadata::StatusKind::open; }
            metadata risk : RiskMetadata::Risk;
        }
        part commandContextFault : ReviewRow subsets modes {
            ref part :>> affected = BlueDog::Architecture::missionContext.boat.control.missionManager;
            attribute :>> identifier = "FM-014";
            attribute :>> intendedFunction = "Apply only current authorized actuation";
            occurrence failureModeEvent : FailureAnalysis::Event { attribute :>> description = "Stale, replayed or mismatched permission/command is accepted"; }
            ref occurrence :>> failureMode = failureModeEvent;
            occurrence causeEvent : FailureAnalysis::Event { attribute :>> description = "Clock, restart, configuration or authority disagreement"; }
            ref occurrence :>> cause = causeEvent;
            occurrence localEffectEvent : FailureAnalysis::Event { attribute :>> description = "Actuation bypasses current restrictions"; }
            ref occurrence :>> localEffect = localEffectEvent;
            occurrence missionEffectEvent : FailureAnalysis::Event { attribute :>> description = "Unintended motion, contact hazard or disqualification"; }
            ref occurrence :>> missionEffect = missionEffectEvent;
            attribute :>> proposedDetection = "Consumer context/ordering/inhibit checks; implementation unverified";
            attribute :>> recommendedAction = "Fault inject expiry, replay, restart and missing durable acknowledgment at physical enable boundary";
            attribute :>> ownerRole = "Autonomy/recovery";
            attribute :>> safetyCritical = true;
            metadata workStatus : ModelingMetadata::StatusInfo { status = ModelingMetadata::StatusKind::open; }
            metadata risk : RiskMetadata::Risk;
        }
        part commonSensingFault : ReviewRow subsets modes {
            ref part :>> affected = BlueDog::Architecture::missionContext.boat.navigation.traffic;
            attribute :>> identifier = "FM-015";
            attribute :>> intendedFunction = "Preserve required observation across primary failure";
            occurrence failureModeEvent : FailureAnalysis::Event { attribute :>> description = "Primary and recovery observations share an undetected failure"; }
            ref occurrence :>> failureMode = failureModeEvent;
            occurrence causeEvent : FailureAnalysis::Event { attribute :>> description = "Common visibility, clock, configuration, software or installation dependence"; }
            ref occurrence :>> cause = causeEvent;
            occurrence localEffectEvent : FailureAnalysis::Event { attribute :>> description = "Both paths supply absent or plausible incorrect observations"; }
            ref occurrence :>> localEffect = localEffectEvent;
            occurrence missionEffectEvent : FailureAnalysis::Event { attribute :>> description = "Required lookout/navigation unavailable during sailing or recovery"; }
            ref occurrence :>> missionEffect = missionEffectEvent;
            attribute :>> proposedDetection = "Independent references and mode-specific coverage evidence; unresolved";
            attribute :>> recommendedAction = "Assess shared dependencies and inject correlated sensing/context failures in upright and inverted modes";
            attribute :>> ownerRole = "Sensing/system safety";
            attribute :>> safetyCritical = true;
            metadata workStatus : ModelingMetadata::StatusInfo { status = ModelingMetadata::StatusKind::open; }
            metadata risk : RiskMetadata::Risk;
        }
    }
    dependency hullLeakDesign from starter::hullLeak to BlueDog::Architecture::missionContext::boat::hullAndRig::printedHull;
    dependency hullLeakCriterion from starter::hullLeak to BlueDogRequirements::enclosureSealing;
    dependency keelLossDesign from starter::keelLoss to BlueDog::Architecture::missionContext::boat::hullAndRig::keelAndBallast;
    dependency keelLossCriterion from starter::keelLoss to BlueDogRequirements::selfRighting;
    dependency steeringJamDesign from starter::steeringJam to BlueDog::Architecture::missionContext::boat::actuation;
    dependency steeringJamCriterion from starter::steeringJam to BlueDogRequirements::weedSnagSteeringRecovery;
    dependency sailJamDesign from starter::sailJam to BlueDog::Architecture::missionContext::boat::actuation;
    dependency sailJamCriterion from starter::sailJam to BlueDogRequirements::sailCommandCadence;
    dependency batteryFaultDesign from starter::batteryFault to BlueDog::Architecture::missionContext::boat::energy::storage;
    dependency batteryFaultCriterion from starter::batteryFault to BlueDogRequirements::sustainedReserveProtection;
    dependency harvestLossDesign from starter::harvestLoss to BlueDog::Architecture::missionContext::boat::energy::harvesting;
    dependency harvestLossCriterion from starter::harvestLoss to BlueDogRequirements::lowEnergyEntry;
    dependency powerCommonCauseDesign from starter::powerCommonCause to BlueDog::Architecture::missionContext::boat::energy::powerManagement;
    dependency powerCommonCauseCriterion from starter::powerCommonCause to BlueDogRequirements::missionReliability;
    dependency navigationFaultDesign from starter::navigationFault to BlueDog::Architecture::missionContext::boat::navigation::positionAndAttitude;
    dependency navigationFaultCriterion from starter::navigationFault to BlueDogRequirements::navigationAvailability;
    dependency controlLockupDesign from starter::controlLockup to BlueDog::Architecture::missionContext::boat::control::missionManager;
    dependency controlLockupCriterion from starter::controlLockup to BlueDogRequirements::resetRecovery;
    dependency trafficMissDesign from starter::trafficMiss to BlueDog::Architecture::missionContext::boat::control::collisionAvoidance;
    dependency trafficMissCriterion from starter::trafficMiss to BlueDogRequirements::trafficSafety;
    dependency radioLossDesign from starter::radioLoss to BlueDog::Architecture::missionContext::boat::communications::telemetryRadio;
    dependency radioLossCriterion from starter::radioLoss to BlueDogRequirements::outageAutonomy;
    dependency motorUncommandedDesign from starter::motorUncommanded to BlueDog::Architecture::missionContext::boat::recovery::motorSystem;
    dependency motorUncommandedCriterion from starter::motorUncommanded to BlueDogRequirements::challengeMotorInhibition;
    dependency dispositionCriterion from DesignFailureReview to BlueDogRequirements::criticalFailureDisposition;
    dependency speedExposureFeedback from DesignFailureReview to BlueDogReliability::CruiseReliability;
    dependency commonCauseBudget from starter::powerCommonCause to BlueDogRequirements::failureRateBudget;
    connection hullLeak_cause_failureMode : CauseAndEffect::Causation connect starter.hullLeak.cause to starter.hullLeak.failureMode;
    connection hullLeak_failureMode_localEffect : CauseAndEffect::Causation connect starter.hullLeak.failureMode to starter.hullLeak.localEffect;
    connection hullLeak_localEffect_missionEffect : CauseAndEffect::Causation connect starter.hullLeak.localEffect to starter.hullLeak.missionEffect;
    connection keelLoss_cause_failureMode : CauseAndEffect::Causation connect starter.keelLoss.cause to starter.keelLoss.failureMode;
    connection keelLoss_failureMode_localEffect : CauseAndEffect::Causation connect starter.keelLoss.failureMode to starter.keelLoss.localEffect;
    connection keelLoss_localEffect_missionEffect : CauseAndEffect::Causation connect starter.keelLoss.localEffect to starter.keelLoss.missionEffect;
    connection steeringJam_cause_failureMode : CauseAndEffect::Causation connect starter.steeringJam.cause to starter.steeringJam.failureMode;
    connection steeringJam_failureMode_localEffect : CauseAndEffect::Causation connect starter.steeringJam.failureMode to starter.steeringJam.localEffect;
    connection steeringJam_localEffect_missionEffect : CauseAndEffect::Causation connect starter.steeringJam.localEffect to starter.steeringJam.missionEffect;
    connection sailJam_cause_failureMode : CauseAndEffect::Causation connect starter.sailJam.cause to starter.sailJam.failureMode;
    connection sailJam_failureMode_localEffect : CauseAndEffect::Causation connect starter.sailJam.failureMode to starter.sailJam.localEffect;
    connection sailJam_localEffect_missionEffect : CauseAndEffect::Causation connect starter.sailJam.localEffect to starter.sailJam.missionEffect;
    connection batteryFault_cause_failureMode : CauseAndEffect::Causation connect starter.batteryFault.cause to starter.batteryFault.failureMode;
    connection batteryFault_failureMode_localEffect : CauseAndEffect::Causation connect starter.batteryFault.failureMode to starter.batteryFault.localEffect;
    connection batteryFault_localEffect_missionEffect : CauseAndEffect::Causation connect starter.batteryFault.localEffect to starter.batteryFault.missionEffect;
    connection harvestLoss_cause_failureMode : CauseAndEffect::Causation connect starter.harvestLoss.cause to starter.harvestLoss.failureMode;
    connection harvestLoss_failureMode_localEffect : CauseAndEffect::Causation connect starter.harvestLoss.failureMode to starter.harvestLoss.localEffect;
    connection harvestLoss_localEffect_missionEffect : CauseAndEffect::Causation connect starter.harvestLoss.localEffect to starter.harvestLoss.missionEffect;
    connection powerCommonCause_cause_failureMode : CauseAndEffect::Causation connect starter.powerCommonCause.cause to starter.powerCommonCause.failureMode;
    connection powerCommonCause_failureMode_localEffect : CauseAndEffect::Causation connect starter.powerCommonCause.failureMode to starter.powerCommonCause.localEffect;
    connection powerCommonCause_localEffect_missionEffect : CauseAndEffect::Causation connect starter.powerCommonCause.localEffect to starter.powerCommonCause.missionEffect;
    connection navigationFault_cause_failureMode : CauseAndEffect::Causation connect starter.navigationFault.cause to starter.navigationFault.failureMode;
    connection navigationFault_failureMode_localEffect : CauseAndEffect::Causation connect starter.navigationFault.failureMode to starter.navigationFault.localEffect;
    connection navigationFault_localEffect_missionEffect : CauseAndEffect::Causation connect starter.navigationFault.localEffect to starter.navigationFault.missionEffect;
    connection controlLockup_cause_failureMode : CauseAndEffect::Causation connect starter.controlLockup.cause to starter.controlLockup.failureMode;
    connection controlLockup_failureMode_localEffect : CauseAndEffect::Causation connect starter.controlLockup.failureMode to starter.controlLockup.localEffect;
    connection controlLockup_localEffect_missionEffect : CauseAndEffect::Causation connect starter.controlLockup.localEffect to starter.controlLockup.missionEffect;
    connection trafficMiss_cause_failureMode : CauseAndEffect::Causation connect starter.trafficMiss.cause to starter.trafficMiss.failureMode;
    connection trafficMiss_failureMode_localEffect : CauseAndEffect::Causation connect starter.trafficMiss.failureMode to starter.trafficMiss.localEffect;
    connection trafficMiss_localEffect_missionEffect : CauseAndEffect::Causation connect starter.trafficMiss.localEffect to starter.trafficMiss.missionEffect;
    connection radioLoss_cause_failureMode : CauseAndEffect::Causation connect starter.radioLoss.cause to starter.radioLoss.failureMode;
    connection radioLoss_failureMode_localEffect : CauseAndEffect::Causation connect starter.radioLoss.failureMode to starter.radioLoss.localEffect;
    connection radioLoss_localEffect_missionEffect : CauseAndEffect::Causation connect starter.radioLoss.localEffect to starter.radioLoss.missionEffect;
    connection motorUncommanded_cause_failureMode : CauseAndEffect::Causation connect starter.motorUncommanded.cause to starter.motorUncommanded.failureMode;
    connection motorUncommanded_failureMode_localEffect : CauseAndEffect::Causation connect starter.motorUncommanded.failureMode to starter.motorUncommanded.localEffect;
    connection motorUncommanded_localEffect_missionEffect : CauseAndEffect::Causation connect starter.motorUncommanded.localEffect to starter.motorUncommanded.missionEffect;

    dependency recoveryCaptureFaultCriterion from starter::recoveryCaptureFault to BlueDogRequirements::soloRetrieval;
    connection recoveryCaptureFault_cause_failureMode : CauseAndEffect::Causation connect starter.recoveryCaptureFault.cause to starter.recoveryCaptureFault.failureMode;
    connection recoveryCaptureFault_failureMode_localEffect : CauseAndEffect::Causation connect starter.recoveryCaptureFault.failureMode to starter.recoveryCaptureFault.localEffect;
    connection recoveryCaptureFault_localEffect_missionEffect : CauseAndEffect::Causation connect starter.recoveryCaptureFault.localEffect to starter.recoveryCaptureFault.missionEffect;
    dependency commandContextFaultCriterion from starter::commandContextFault to BlueDogRequirements::commandIntegrity;
    connection commandContextFault_cause_failureMode : CauseAndEffect::Causation connect starter.commandContextFault.cause to starter.commandContextFault.failureMode;
    connection commandContextFault_failureMode_localEffect : CauseAndEffect::Causation connect starter.commandContextFault.failureMode to starter.commandContextFault.localEffect;
    connection commandContextFault_localEffect_missionEffect : CauseAndEffect::Causation connect starter.commandContextFault.localEffect to starter.commandContextFault.missionEffect;
    dependency commonSensingFaultCriterion from starter::commonSensingFault to BlueDogRequirements::trafficSafety;
    connection commonSensingFault_cause_failureMode : CauseAndEffect::Causation connect starter.commonSensingFault.cause to starter.commonSensingFault.failureMode;
    connection commonSensingFault_failureMode_localEffect : CauseAndEffect::Causation connect starter.commonSensingFault.failureMode to starter.commonSensingFault.localEffect;
    connection commonSensingFault_localEffect_missionEffect : CauseAndEffect::Causation connect starter.commonSensingFault.localEffect to starter.commonSensingFault.missionEffect;
}

package BlueDogEncounterEnvelope {
    private import ScalarValues::*;
    doc /* Historical six-class 750 m response-distance comparison, not the current BlueDogClassDetection allocation or sensor qualification. Distances start at the nearest relevant physical extent, including the whole tow or swept underwater hazard. Velocities share a ground-relative frame. The scalar relative-speed bound must cover motion throughout response; turns or acceleration require a supported bound or trajectory assessment. No collision-free maneuver is proved.*/

    calc def RelativeSpeed {
        in ownEastMps : Real;
        in ownNorthMps : Real;
        in targetEastMps : Real;
        in targetNorthMps : Real;
        return speedMps : Real = RealFunctions::sqrt(
            (targetEastMps-ownEastMps)*(targetEastMps-ownEastMps)
            +(targetNorthMps-ownNorthMps)*(targetNorthMps-ownNorthMps));
    }

    calc def ResponseAfterDelivery {
        doc /* busyAtDeliveryS is residual occupancy WHEN the usable observation
         * reaches guidance, not at envelope entry. Acquisition and delivery must
         * be disjoint measured intervals. Phase is the next eligible assessment
         * opportunity after both observation availability and controller release.
         * The old one-second assessment allocation is counted here ONCE; there
         * is no additional one-second processing term. New command and avoidance
         * duration are separate from the remaining OLD command/maneuver. */
        in acquisitionS : Real;
        in deliveryS : Real;
        in busyAtDeliveryS : Real;
        in assessmentPhaseS : Real;
        in commandS : Real;
        in avoidanceS : Real;
        in contingencyS : Real;
        return seconds : Real = acquisitionS+deliveryS+busyAtDeliveryS
            +assessmentPhaseS+commandS+avoidanceS+contingencyS;
    }

    calc def ResponseFromEntry {
        doc /* busyAtEntryS is time until release measured at envelope entry.
         * Observation production overlaps that ONE known occupied interval.
         * This branch assumes no new unrelated maneuver starts before observation
         * delivery; use a residual-at-delivery bound otherwise. Phase is charged
         * once, after the later of observation delivery and controller release. */
        in acquisitionS : Real;
        in deliveryS : Real;
        in busyAtEntryS : Real;
        in assessmentPhaseS : Real;
        in commandS : Real;
        in avoidanceS : Real;
        in contingencyS : Real;
        attribute readyS : Real = acquisitionS+deliveryS;
        return seconds : Real = (if readyS > busyAtEntryS ? readyS else busyAtEntryS)
            +assessmentPhaseS+commandS+avoidanceS+contingencyS;
    }

    calc def RangeForResponse {
        in relativeSpeedMps : Real;
        in responseS : Real;
        in separationM : Real;
        in positionAllowanceM : Real;
        return rangeM : Real = relativeSpeedMps*responseS+separationM+positionAllowanceM;
    }

    analysis def Envelope {
        subject encounter;
        doc /* Caller supplies supported bounds, not nominal turn time. Set motionBoundAvailable=false for stalled or unresolved maneuver authority and observationBoundAvailable=false for presence-only/unbounded tracks. Unsupported distances are -1. occupiedAtDelivery selects the epoch of occupiedS. This scalar necessary timing screen does not prove safe motion or rules compliance. appliesTrafficRequirement selects the historical six-class comparison scope, excluding weeds. Its retained 750 m floor is historical only; current BlueDogClassDetection policy has no such floor.*/
        in attribute ownEastMps : Real;
        in attribute ownNorthMps : Real;
        in attribute targetEastMps : Real;
        in attribute targetNorthMps : Real;
        in attribute acquisitionS : Real;
        in attribute deliveryS : Real;
        in attribute occupiedS : Real;
        in attribute occupiedAtDelivery : Boolean;
        in attribute assessmentPhaseS : Real;
        in attribute commandS : Real;
        in attribute avoidanceS : Real;
        in attribute contingencyS : Real;
        in attribute separationM : Real;
        in attribute positionAllowanceM : Real;
        in attribute motionBoundAvailable : Boolean;
        in attribute observationBoundAvailable : Boolean;
        in attribute appliesTrafficRequirement : Boolean;
        out attribute supported : Boolean = motionBoundAvailable and observationBoundAvailable
        and acquisitionS >= 0 and deliveryS >= 0 and occupiedS >= 0
        and assessmentPhaseS >= 0 and commandS >= 0 and avoidanceS >= 0
        and contingencyS >= 0 and separationM >= 0 and positionAllowanceM >= 0;
        out attribute relativeSpeedMps : Real = RelativeSpeed(ownEastMps,ownNorthMps,targetEastMps,targetNorthMps);
        out attribute responseSeconds : Real = if not supported ? -1
        else if occupiedAtDelivery ? ResponseAfterDelivery(acquisitionS,deliveryS,occupiedS,assessmentPhaseS,commandS,avoidanceS,contingencyS)
        else ResponseFromEntry(acquisitionS,deliveryS,occupiedS,assessmentPhaseS,commandS,avoidanceS,contingencyS);
        out attribute requiredRangeM : Real = if supported ? RangeForResponse(relativeSpeedMps,responseSeconds,separationM,positionAllowanceM) else -1;
        out attribute retainedRequirementM : Real = BlueDogEncounterReview::criteria.rangeAllocationM;
        out attribute trafficComparisonApplicable : Boolean = appliesTrafficRequirement;
        out attribute fitsRetainedDistance : Boolean = appliesTrafficRequirement and supported and requiredRangeM <= retainedRequirementM;
        out attribute combinedEnvelopeM : Real = if not supported ? -1 else if not appliesTrafficRequirement ? requiredRangeM else if requiredRangeM > retainedRequirementM ? requiredRangeM else retainedRequirementM;
        out attribute status : String = if not supported ? "Unsupported: no finite response-distance claim" else if not appliesTrafficRequirement ? "Scenario timing sensitivity only; historical 750 m traffic comparison not applicable" else if fitsRetainedDistance ? "Within historical 750 m timing budget only; no current acceptance" else "Exceeds historical 750 m comparison; current class allocation remains open";
        out attribute physicalQualification : Boolean = false;
    }

    part study {
        attribute acquisitionS : Real = BlueDogEncounterReview::criteria.acquisitionSeconds;
        attribute deliveryS : Real = BlueDogIntegratedCandidate::hypothesis.sensorLatencyS;
        attribute assessmentPhaseS : Real = BlueDogEncounterReview::criteria.assessmentSeconds;
        attribute commandS : Real = BlueDogEncounterReview::criteria.commandSeconds;
        attribute avoidanceS : Real = BlueDogEncounterReview::criteria.maneuverSeconds;
        attribute contingencyS : Real = BlueDogEncounterReview::criteria.reserveSeconds;
        attribute positionAllowanceM : Real = BlueDogEncounterReview::criteria.relativePositionAllowanceM;
        attribute ownSpeedMps : Real = BlueDogEncounterReview::criteria.vesselSpeedMps;
        attribute illustrativeOccupiedS : Real = commandS+avoidanceS;
        attribute retainedRequirementM : Real = BlueDogEncounterReview::criteria.rangeAllocationM;
        attribute targets : String [8] ordered = (
            "commercial tow including barges", "fishing or drifting craft",
            "fast craft including towed person", "sailing craft", "passenger vessel",
            "person or low-profile paddle craft", "stationary person or low-profile paddle craft", "weed boundary");
        attribute targetSpeedMps : Real [8] ordered nonunique = (
            BlueDogEncounterReview::criteria.targetSpeedMps#(1),
            BlueDogEncounterReview::criteria.targetSpeedMps#(2),
            BlueDogEncounterReview::criteria.targetSpeedMps#(3),
            BlueDogEncounterReview::criteria.targetSpeedMps#(4),
            BlueDogEncounterReview::criteria.targetSpeedMps#(5),
            BlueDogEncounterReview::criteria.targetSpeedMps#(6),0,0);
        attribute separationM : Real [8] ordered nonunique = (
            BlueDogEncounterReview::criteria.hullSeparationM#(1),
            BlueDogEncounterReview::criteria.hullSeparationM#(2),
            BlueDogEncounterReview::criteria.hullSeparationM#(3),
            BlueDogEncounterReview::criteria.hullSeparationM#(4),
            BlueDogEncounterReview::criteria.hullSeparationM#(5),
            BlueDogEncounterReview::criteria.hullSeparationM#(6),
            BlueDogEncounterReview::criteria.hullSeparationM#(6),0);
        attribute additionalClassScope : String = "Stationary person or low-profile paddle craft retains its traffic separation and acquisition requirement. Weed row is a stationary no-contact boundary sensitivity with the existing 10 m position allowance, not a selected weed stand-off or an extension of the traffic acquisition requirement. Moving mats need measured ground velocity; fixed vegetation and drifting vegetation are different cases.";
        attribute occupiedScope : String = "17 s illustrates the archived 2 s command plus 15 s hold only. New bounded-turn dynamics may take longer or stall; substitute an achieved supported residual and avoidance bound or report unsupported.";
    }

    analysis Summary {
        out attribute targets : String [8] ordered = study.targets;
        out attribute targetSpeedMps : Real [8] ordered nonunique = study.targetSpeedMps;
        out attribute ownSpeedMps : Real = study.ownSpeedMps;
        out attribute separationM : Real [8] ordered nonunique = study.separationM;
        out attribute retainedRequirementM : Real = study.retainedRequirementM;
        out attribute freshSeconds : Real = ResponseAfterDelivery(study.acquisitionS,study.deliveryS,0,study.assessmentPhaseS,study.commandS,study.avoidanceS,study.contingencyS);
        out attribute occupiedAtEntrySeconds : Real = ResponseFromEntry(study.acquisitionS,study.deliveryS,study.illustrativeOccupiedS,study.assessmentPhaseS,study.commandS,study.avoidanceS,study.contingencyS);
        out attribute occupiedAtDeliverySeconds : Real = ResponseAfterDelivery(study.acquisitionS,study.deliveryS,study.illustrativeOccupiedS,study.assessmentPhaseS,study.commandS,study.avoidanceS,study.contingencyS);
        out attribute headOnFreshM : Real [8] ordered nonunique = (1..8)->ControlFunctions::collect {
            in i : Integer; RangeForResponse(RelativeSpeed(study.ownSpeedMps,0,-study.targetSpeedMps#(i),0),freshSeconds,study.separationM#(i),study.positionAllowanceM) };
        out attribute crossingFreshM : Real [8] ordered nonunique = (1..8)->ControlFunctions::collect {
            in i : Integer; RangeForResponse(RelativeSpeed(study.ownSpeedMps,0,0,study.targetSpeedMps#(i)),freshSeconds,study.separationM#(i),study.positionAllowanceM) };
        out attribute sameCourseFreshM : Real [8] ordered nonunique = (1..8)->ControlFunctions::collect {
            in i : Integer; RangeForResponse(RelativeSpeed(study.ownSpeedMps,0,study.targetSpeedMps#(i),0),freshSeconds,study.separationM#(i),study.positionAllowanceM) };
        out attribute headOnOccupiedAtEntryM : Real [8] ordered nonunique = (1..8)->ControlFunctions::collect {
            in i : Integer; RangeForResponse(RelativeSpeed(study.ownSpeedMps,0,-study.targetSpeedMps#(i),0),occupiedAtEntrySeconds,study.separationM#(i),study.positionAllowanceM) };
        out attribute headOnOccupiedAtDeliveryM : Real [8] ordered nonunique = (1..8)->ControlFunctions::collect {
            in i : Integer; RangeForResponse(RelativeSpeed(study.ownSpeedMps,0,-study.targetSpeedMps#(i),0),occupiedAtDeliverySeconds,study.separationM#(i),study.positionAllowanceM) };
        out attribute ownSpeedSweepMps : Real [5] ordered = (0,0.5,1,2,3);
        out attribute fastHeadOnByOwnSpeedM : Real [5] ordered nonunique = ownSpeedSweepMps->ControlFunctions::collect {
            in speed : Real; RangeForResponse(RelativeSpeed(speed,0,-study.targetSpeedMps#(3),0),freshSeconds,study.separationM#(3),study.positionAllowanceM) };
        out attribute qualificationClaim : Boolean = false;
        out attribute scope : String = "Historical six-class 750 m comparison and constant/bounded relative-velocity sensitivity, not current BlueDogClassDetection acceptance. Own-speed sweep alone does not preserve maneuver authority. No sensor measurement is credited.";
    }

    part observationContract {
        attribute presence : String = "First establish that a relevant hazard exists, with detection/miss and false-alarm evidence for its class, bearing, illumination and obscuration. Absence of AIS is not absence of a target.";
        attribute bearing : String = "Bearing and uncertainty place the hazard relative to the course and swept vessel; all-bearing coverage must address rig occlusion. Bearing alone does not give metric range.";
        attribute range : String = "Range and uncertainty are to the nearest relevant physical extent, not an AIS antenna or a circular proxy that detects early. Tow/skier envelopes and submerged appendages must be included.";
        attribute relativeMotion : String = "Time-stamped range/bearing or an independently supported velocity estimate must bound closing motion and intent changes. One image, presence detection or a passive acoustic cue does not establish range rate or a collision track.";
        attribute geometry : String = "Head-on adds speeds, right-angle crossing uses vector relative speed, and same-course overtaking uses speed difference. These are collision-course sensitivity geometries; other bearings require closest-approach and swept-motion assessment. Unknown target intent requires an adverse supported velocity envelope.";
        attribute lowTargets : String = "People, paddlers and stationary low obstacles need their own detection and range evidence in glare, waves and darkness. Commercial-vessel detection does not transfer to them.";
        attribute weeds : String = "Resolve vegetation extent and depth relative to keel, rudder and propulsor sweep, including sparse strands and moving mats. Presence or a downward survey return after passage is not timely forward clearance evidence.";
    }

    dependency unchangedAcquisition from Envelope to BlueDogRequirements::trafficSafety;
    dependency observedTracks from observationContract to BlueDogRequirements::trafficTracking;
    dependency responseDeadline from Envelope to BlueDogRequirements::avoidanceCommandDeadline;
    dependency archivedBudget from Summary to BlueDogEncounterReview::criteria;
}

package BlueDogEncounterFeasibility {
    private import ScalarValues::*;
    doc /* Historical six-class acquisition comparison retained for archived evidence reproduction. The uniform 750 m allocation and broad low-target class are prior hypotheses, not current acceptance criteria. Current class-specific policy and open review/evidence gates are BlueDogClassDetection; these numerical APIs retain their historical meaning.*/
    calc def RequiredRange {
        in closingMps : Real;
        in acquisitionS : Real;
        in processingS : Real;
        in commandS : Real;
        in maneuverS : Real;
        in contingencyS : Real;
        in separationM : Real;
        in errorM : Real;
        return rangeM : Real = closingMps*(acquisitionS+processingS+commandS+maneuverS+contingencyS)+separationM+errorM;
    }
    calc def EnergyScreen {
        in additionalBusW : Real;
        return headroomWh : Real = BlueDogCandidateEnergy::headroom.energyWh-additionalBusW*BlueDogCandidateEnergy::exposureHours/BlueDogSRRCurrent::energyInputs.dischargeEfficiency;
    }
    calc def InstalledIncrement {
        in measuredBusW : Real;
        in replacedBaseW : Real;
        return incrementW : Real = measuredBusW-replacedBaseW;
    }
    calc def CapacityLowerBound {
        in incrementW : Real;
        return nameplateWh : Real = (BlueDogCandidateEnergy::required.energyWh+incrementW*BlueDogCandidateEnergy::exposureHours/BlueDogSRRCurrent::energyInputs.dischargeEfficiency)/(BlueDogSRRCurrent::energyInputs.usableFraction*BlueDogSRRCurrent::energyInputs.initialFraction);
    }
    requirement def TimingCriterion {
        subject target;
        in attribute assessmentPeriodS : Real;
        in attribute commandLatencyS : Real;
        require constraint { assessmentPeriodS > 0 and assessmentPeriodS <= BlueDogEncounterReview::criteria.assessmentSeconds and commandLatencyS >= 0 and commandLatencyS <= BlueDogEncounterReview::criteria.commandSeconds }
    }
    analysis Inputs {
        out attribute targets : String [6] ordered = BlueDogEncounterReview::criteria.targets;
        out attribute speeds : Real [6] ordered nonunique = BlueDogEncounterReview::criteria.targetSpeedMps;
        out attribute separations : Real [6] ordered nonunique = BlueDogEncounterReview::criteria.hullSeparationM;
        out attribute ownSpeed : Real = BlueDogEncounterReview::criteria.vesselSpeedMps;
        out attribute acquisition : Real = BlueDogEncounterReview::criteria.acquisitionSeconds;
        out attribute processing : Real = BlueDogEncounterReview::criteria.assessmentSeconds;
        out attribute command : Real = BlueDogEncounterReview::criteria.commandSeconds;
        out attribute contingency : Real = BlueDogEncounterReview::criteria.reserveSeconds;
        out attribute error : Real = BlueDogEncounterReview::criteria.relativePositionAllowanceM;
        out attribute rangeAllocation : Real = BlueDogEncounterReview::criteria.rangeAllocationM;
        out attribute maneuverSweep : Real [3] ordered = (15,30,60);
        out attribute processingSweep : Real [3] ordered = (1,5,15);
        out attribute stacks : String [4] ordered = ("AIS + vision", "AIS + radar + vision", "AIS + hydrophone cue + vision", "AIS + forward sonar + vision");
        // Deliberately hypothetical combined envelopes, no vendor performance credit.
        out attribute craftRange : Real [4] ordered nonunique = (250,750,250,250);
        out attribute lowRange : Real [4] ordered nonunique = (100,150,100,100);
        out attribute weedRange : Real [4] ordered nonunique = (20,20,20,40);
        out attribute cooperativeRange : Real = 1500;
        out attribute nightFactor : Real [4] ordered nonunique = (0.3,0.8,0.3,0.3);
        out attribute latency : Real [4] ordered nonunique = (2,1,3,2);
        out attribute additionalBusW : Real [4] ordered nonunique = (3,8,5,10);
        out attribute usableBatteryWh : Real = BlueDogCandidateEnergy::usable.energyWh;
        out attribute trialHorizonS : Real = 120;
        out attribute continuationHorizonS : Real = 3600;
        out attribute controllerSweepS : Real [2] ordered = (30,1);
        out attribute commandLatencyS : Real = BlueDogEncounterReview::criteria.commandSeconds;
        out attribute refinementStepS : Real [2] ordered = (1,0.5);
        out attribute clearanceTailS : Real = 60;
        out attribute baselineElectronicsW : Real = BlueDogCandidateEnergy::electronics.averageBusW;
        out attribute trialSeeds : Integer [2] ordered = (17,29);
        out attribute recoveryCapability : Real [5] ordered nonunique = (2,50,8,1.2,2);
        out attribute samplePeriodS : Real = 1;
        out attribute missProbability : Real = 0.1;
        out attribute positionErrorM : Real = 5;
        out attribute trackExpiryS : Real = 10;
    }
    part def RangeRow {
        attribute targetIndex : Integer;
        attribute target : String = BlueDogEncounterReview::criteria.targets#(targetIndex);
        attribute baselineM : Real = RequiredRange(BlueDogEncounterReview::criteria.targetSpeedMps#(targetIndex)+Inputs.ownSpeed,Inputs.acquisition,Inputs.processing,Inputs.command,15,Inputs.contingency,BlueDogEncounterReview::criteria.hullSeparationM#(targetIndex),Inputs.error);
        attribute slowerM : Real = RequiredRange(BlueDogEncounterReview::criteria.targetSpeedMps#(targetIndex)+Inputs.ownSpeed,Inputs.acquisition,Inputs.processing,Inputs.command,30,Inputs.contingency,BlueDogEncounterReview::criteria.hullSeparationM#(targetIndex),Inputs.error);
    }
    part def StackRow {
        attribute stackIndex : Integer;
        attribute label : String = Inputs.stacks#(stackIndex);
        attribute craftM : Real = Inputs.craftRange#(stackIndex);
        attribute lowM : Real = Inputs.lowRange#(stackIndex);
        attribute weedM : Real = Inputs.weedRange#(stackIndex);
        attribute additionalW : Real = Inputs.additionalBusW#(stackIndex);
        attribute headroomWh : Real = EnergyScreen(additionalW);
    }
    part target1 : RangeRow { attribute :>> targetIndex = 1; }
    part target2 : RangeRow { attribute :>> targetIndex = 2; }
    part target3 : RangeRow { attribute :>> targetIndex = 3; }
    part target4 : RangeRow { attribute :>> targetIndex = 4; }
    part target5 : RangeRow { attribute :>> targetIndex = 5; }
    part target6 : RangeRow { attribute :>> targetIndex = 6; }
    part stack1 : StackRow { attribute :>> stackIndex = 1; }
    part stack2 : StackRow { attribute :>> stackIndex = 2; }
    part stack3 : StackRow { attribute :>> stackIndex = 3; }
    part stack4 : StackRow { attribute :>> stackIndex = 4; }
    dependency timingBasis from TimingCriterion to BlueDogRequirements::avoidanceCommandDeadline;
    dependency loadBasis from InstalledIncrement to BlueDogCandidateEnergy::electronics;
    dependency rangeBasis from RequiredRange to BlueDogEncounterReview::criteria;
    dependency energyBasis from EnergyScreen to BlueDogCandidateEnergy::Reconciliation;
    dependency riskBasis from Inputs to BlueDogRisks::traffic;
}

package BlueDogEncounterReview {
    doc /* Historical six-class acquisition comparison retained for archived evidence reproduction. The uniform 750 m allocation and broad low-target class are prior hypotheses, not current acceptance criteria. Current class-specific policy and open review/evidence gates are BlueDogClassDetection; these numerical APIs retain their historical meaning.*/
    private import ScalarValues::*;
    part criteria {
        attribute targets : String [6] ordered = ("tow including barges", "fishing or drifting craft", "ski/power boat including tow", "sailing craft", "passenger vessel", "person or low-profile paddle craft");
        attribute targetSpeedMps : Real [6] ordered nonunique = (3.5,1.5,15,4,4,2);
        attribute lengthM : Real [6] ordered nonunique = (180,6,30,8,100,2);
        attribute beamM : Real [6] ordered nonunique = (24,2.5,3,3,18,1);
        attribute hullSeparationM : Real [6] ordered nonunique = (50,20,30,20,50,20);
        attribute vesselSpeedMps : Real = 3;
        attribute acquisitionSeconds : Real = 5;
        attribute assessmentSeconds : Real = 1;
        attribute commandSeconds : Real = 2;
        attribute maneuverSeconds : Real = 15;
        attribute reserveSeconds : Real = 15;
        attribute relativePositionAllowanceM : Real = 10;
        attribute rangeAllocationM : Real = 750;
        attribute visibilityM : Real = 1000;
        metadata rationale : ModelingMetadata::Rationale { text = "Engineering acceptance cases, not measured traffic rates or statutory separation. Range is measured from the nearest physical target extent, not an AIS antenna; use the whole tow and skier envelope. Closing speed is target speed plus 3 m/s vessel speed. Allow 5 s acquisition, 1 s assessment, 2 s command, 15 s maneuver and 15 s contingency, plus 10 m relative position error and class separation. Worst allocated closing case requires 724 m, rounded to 750 m. Observe all bearings including mast/wing occlusion in daylight, darkness, glare and 1 km visibility; include low freeboard paddle craft and a person-sized target. No AIS dependence. If capability is not demonstrable, reduce admissible speed/exposure with the same equation or redesign detection; do not waive collision avoidance."; }
    }
    analysis Acquisition {
        out attribute requiredRangesM : Real [6] ordered nonunique = (1..6)->ControlFunctions::collect {
            in i : Integer;
            BlueDogEncounterFeasibility::RequiredRange(criteria.targetSpeedMps#(i)+criteria.vesselSpeedMps,criteria.acquisitionSeconds,criteria.assessmentSeconds,criteria.commandSeconds,criteria.maneuverSeconds,criteria.reserveSeconds,criteria.hullSeparationM#(i),criteria.relativePositionAllowanceM) };
    }
    part acceptance {
        attribute scenarios : String = "Both tacks; head-on, crossing each side, overtaking each side, anchored/drifting fishing, reversing ski boat, obscured emergence, dense traffic, bridge approach and casualty recovery; repeat by target class in day/night and wave/glare extremes.";
        attribute passCriterion : String = "Historical acceptance hypothesis, not current BlueDogClassDetection policy: Acquire within 5 s of the target entering the 750 m envelope; maintain the track; update risk each second and command within 2 s; demonstrate the allocated maneuver within 15 s or reject the scenario. Independently measured swept hulls shall not overlap, project separation shall be preserved, and a confined vessel shall not need to change speed/course because of Blue Dog. Apply navigation rules separately; passing distance alone is insufficient.";
        attribute simulationScope : String = "Mission traffic generator is coarse route exposure. Exact target truth is not sensor performance. Dedicated deterministic encounter fixtures and later hardware replay close the one-second/2-second requirements; a 30 s mission control period cannot claim them.";
    }
    dependency basis from criteria to BlueDogRequirements::trafficSafety;
    dependency tracking from criteria to BlueDogRequirements::trafficTracking;
    dependency timing from criteria to BlueDogRequirements::avoidanceCommandDeadline;
    dependency applicableNavigationDuties from acceptance to GorgeChallenge::navigationRules;
}

package BlueDogEnergy {
    private import ScalarValues::*;
    public import MarineEnergy::*;
    private import ISQ::*;
    private import SI::*;
    doc /* Battery-bus energy accounting with piecewise-constant bounded loads and
     * harvested power. All calculations execute natively. Interval averaging must
     * resolve outages/load bursts that matter to storage minima; peak demand is
     * checked separately without credit for intermittent harvesting. No controller,
     * weather forecast, electrochemical model or vessel qualification is implied.
     */

    part def Scenario {
        part battery : Battery;
        part intervals : Interval [1..*];
        ref part timeline : Interval [1..*] ordered;
        attribute initialEnergy : EnergyValue;
        attribute recoveryMotorPower : PowerValue;
        attribute recoveryEssentialPower : PowerValue;
        attribute recoveryPoweredDuration : TimeValue;
        attribute recoveryEssentialDuration : TimeValue;
        attribute recoveryUncertaintyFactor : Real;
        attribute reserve : EnergyValue = BlueDogRequirements::RecoveryReserveDemand(recoveryMotorPower, recoveryEssentialPower, recoveryPoweredDuration, recoveryEssentialDuration, recoveryUncertaintyFactor);
        attribute dayCount : Integer;
        attribute evidenceAccepted : Boolean;
        doc /* evidenceAccepted requires the review record defined by BlueDogDesignDecisions::energyEvidenceAcceptance.
         * No default: numerical feasibility and measurement acceptance are distinct.
         * Inputs refer to the same installed configuration. Recovery powers are
         * battery-energy withdrawal rates (include discharge/conversion losses).
         */
    }

    calc def EnergyAt {
        in scenario : Scenario;
        in index : Integer;
        return energy : EnergyValue;
        if index == 0 ? scenario.initialEnergy else
        NumericalFunctions::min(scenario.battery.capacity / (1 [J]),
            (EnergyAt(scenario, index - 1) + StorageRate(scenario.timeline#(index), scenario.battery) * scenario.timeline#(index).duration) / (1 [J])) * 1 [J]
    }
    calc def TimeAt {
        in scenario : Scenario;
        in index : Integer;
        return time : TimeValue;
        if index == 0 ? 0 [s] else TimeAt(scenario, index - 1) + scenario.timeline#(index).duration
    }
    calc def HarvestTimeInDay {
        in scenario : Scenario;
        in day : Integer;
        return enabledTime : TimeValue;
        NumericalFunctions::sum((1..SequenceFunctions::size(scenario.timeline))->ControlFunctions::collect {
            in i : Integer;
            if scenario.timeline#(i).harvestEnabled ?
                NumericalFunctions::max(0, NumericalFunctions::min(TimeAt(scenario, i) / (1 [s]), day * 86400) -
                NumericalFunctions::max(TimeAt(scenario, i - 1) / (1 [s]), (day - 1) * 86400)) * 1 [s]
            else 0 [s]
        })
    }

    analysis def SustainedOperation {
        subject scenario : Scenario;
        attribute count : Integer = SequenceFunctions::size(scenario.timeline);
        out attribute inputsValid : Boolean =
            count > 0 and scenario.dayCount > 0 and scenario.battery.valid and
        scenario.initialEnergy > 0 [J] and scenario.initialEnergy <= scenario.battery.capacity and
        scenario.recoveryMotorPower > 0 [W] and scenario.recoveryEssentialPower > 0 [W] and
        scenario.recoveryPoweredDuration > 0 [s] and scenario.recoveryEssentialDuration >= scenario.recoveryPoweredDuration and scenario.recoveryUncertaintyFactor >= 1 and
        scenario.timeline->ControlFunctions::forAll { in interval : Interval; interval.valid };
        assert constraint validInputs { inputsValid }
        out attribute campaignDuration : TimeValue = TimeAt(scenario, count);
        out attribute usableCapacity : EnergyValue = scenario.battery.capacity;
        out attribute protectedReserve : EnergyValue = scenario.reserve;
        out attribute boundaryTimes : TimeValue [*] ordered nonunique = (0..count)->ControlFunctions::collect { in i : Integer; TimeAt(scenario, i) };
        out attribute energyHistory : EnergyValue [*] ordered nonunique = (0..count)->ControlFunctions::collect { in i : Integer; EnergyAt(scenario, i) };
        out attribute storageRates : PowerValue [*] ordered nonunique = scenario.timeline->ControlFunctions::collect { in interval : Interval; StorageRate(interval, scenario.battery) };
        out attribute reserveMargins : EnergyValue [*] ordered nonunique = energyHistory->ControlFunctions::collect { in e : EnergyValue; e - scenario.reserve };
        out attribute harvestHoursPerDay : Real [*] ordered nonunique = (1..scenario.dayCount)->ControlFunctions::collect { in d : Integer; HarvestTimeInDay(scenario, d) / (3600 [s]) };
        out attribute consumedEnergy : EnergyValue = NumericalFunctions::sum(scenario.timeline->ControlFunctions::collect {
            in interval : Interval; interval.budget.averagePower * interval.duration });
        out attribute harvestedBusEnergy : EnergyValue = NumericalFunctions::sum(scenario.timeline->ControlFunctions::collect {
            in interval : Interval; interval.busHarvestPower * interval.duration });
        out attribute finalStoredEnergy : EnergyValue = EnergyAt(scenario, count);
        out attribute reserveProtected : Boolean = BlueDogRequirements::SustainedReserveProtectionCriterion(energyHistory, scenario.reserve);
        out attribute repeatableBalance : Boolean = BlueDogRequirements::RepeatableCycleBalanceCriterion(scenario.initialEnergy, finalStoredEnergy);
        out attribute peakSupported : Boolean = BlueDogRequirements::PeakSupplyCapabilityCriterion(
            scenario.timeline->ControlFunctions::collect { in interval : Interval; interval.budget.peakPower / scenario.battery.dischargeEfficiency + scenario.battery.selfDischargePower },
            scenario.battery.maxDischargePower);
        out attribute campaignCovered : Boolean = BlueDogRequirements::HarvestCampaignCoverageCriterion(campaignDuration, scenario.dayCount, harvestHoursPerDay);
        out attribute finiteCampaignFeasible : Boolean = inputsValid and reserveProtected and peakSupported;
        return modeledEnergyFeasible : Boolean = finiteCampaignFeasible and repeatableBalance and campaignCovered;
        out attribute evidenceReady : Boolean = BlueDogRequirements::EnergyEvidenceReadinessCriterion(scenario.evidenceAccepted);
        out attribute finiteCampaignSupported : Boolean = finiteCampaignFeasible and evidenceReady;
        out attribute energyCaseSupported : Boolean = modeledEnergyFeasible and evidenceReady;
        objective feasibility {
            doc /* Conditional numerical feasibility only; evidenceReady is separately reported. */
            require constraint { modeledEnergyFeasible }
        }
    }
    dependency sustainedReserveProtectionTrace from SustainedOperation to BlueDogRequirements::sustainedReserveProtection;
    dependency finiteCampaignTrace from SustainedOperation to BlueDogRequirements::multiDayEndurance;
    dependency repeatableCycleBalanceTrace from SustainedOperation to BlueDogRequirements::repeatableCycleBalance;
    dependency peakSupplyCapabilityTrace from SustainedOperation to BlueDogRequirements::peakSupplyCapability;
    dependency harvestCampaignCoverageTrace from SustainedOperation to BlueDogRequirements::harvestCampaignCoverage;
    dependency energyEvidenceReadinessTrace from SustainedOperation to BlueDogRequirements::energyEvidenceReadiness;

    verification def SustainedEnergyVerification {
        metadata plannedAnalyze : VerificationCases::VerificationMethod { kind = VerificationCases::VerificationMethodKind::analyze; }
        doc /* Energy-case verification only. Synthetic or unaccepted evidence is
         * inconclusive even when the numerical analysis passes. This does not verify
         * navigation, sailing performance, weather availability or indefinite life.
         */
        subject scenario : Scenario;
        analysis calculation : SustainedOperation { subject = scenario; }
        objective energyAcceptance {
            verify BlueDogRequirements::sustainedEnergyFeasibility;
            require constraint { calculation.energyCaseSupported }
        }
        return verdict : VerificationCases::VerdictKind =
            if not calculation.evidenceReady ? VerificationCases::VerdictKind::inconclusive
        else VerificationCases::PassIf(calculation.modeledEnergyFeasible);
    }
}

package BlueDogEnvironmentReview {
    private import ScalarValues::*;
    doc /* SRR design-basis review: candidate allocations are not measured extrema,
     * joint occurrence probabilities or accepted launch limits. */
    part evidence {
        attribute windSource : String = "https://repository.library.noaa.gov/view/noaa/28157/noaa_28157_DS1.pdf";
        attribute windFinding : String = "Two cool seasons of profiler observations characterize persistent easterly gap flow and spatial/vertical variation. Gap-jet statistics at Troutdale are not 10 m surface limits for Bingen to Stevenson.";
        attribute surfaceRecord : String = "evidence/weather/2015-2024/manifest.json";
        attribute surfaceLimit : String = "Archived airport observations support seasonal sensitivity; they do not provide a calibrated along-route launch forecast or small-wing exposure.";
        attribute chartSource : String = "evidence/course/2026-10-11/sources.json";
        attribute currentLimit : String = "Chart geometry and pool stage do not establish a local current maximum. Retain 1.5 m/s as a proposed sensitivity bound pending spatial current evidence; recovery routing must reject insufficient authority.";
        attribute waveBasis : String = "MarineSurface::FetchSea; effective fetch 3, 8 and 15 km. These are model sensitivities, not surveyed directional fetch or observed wave statistics.";
        attribute reviewAccepted : Boolean = false;
        metadata issue : ModelingMetadata::Issue { text = "Qualification shall use coupled wind, current and waves plus separate wake events. The SRR allocations define the design domain; measured route profiles and forecast-conditioned exposure are required before field release. Do not infer joint extremes by combining independent maxima or assign return periods without evidence."; }
    }
    part proposed {
        attribute operationalWindUpperMps : Real = 15;
        attribute operationalGustUpperMps : Real = 20;
        attribute operationalWaveHeightM : Real = 1.5;
        attribute operationalPeriodSeconds : Real [2] ordered nonunique = (1.5,5);
        attribute currentSensitivityUpperMps : Real = 1.5;
        attribute includesCalmWaiting : Boolean = true;
        attribute includesDarkness : Boolean = true;
        attribute mandatesProgressAtEveryCondition : Boolean = false;
        attribute recoveryExposureBasis : String = "Course-dependent transit and final retrieval exposure, including forecast deterioration; exposure ends at retained, retrievable shore arrival plus the declared pickup delay. No fixed challenge or survival deadline is imposed.";
        metadata rationale : ModelingMetadata::Rationale { text = "Propose 1.5 m significant wave height and 1.5-5 s peak period for review: the native 6-15 m/s wind, 3-15 km fetch sensitivity yields approximately 0.21-1.22 m and 1.80-4.28 s before current and wakes. The rounding margin is an engineering allocation, not a measured extreme. Retain 15 m/s mean wind, 20 m/s gust and 1.5 m/s current as unaccepted study allocations. Calm waiting is an allowed mission state, not a minimum-wind failure. Dense fog matters through loss of safety capability."; }
    }
    part recovery {
        attribute meanWindUpperMps : Real = 25;
        attribute gustUpperMps : Real = 35;
        attribute significantWaveHeightM : Real = 2;
        attribute peakPeriodSeconds : Real [2] ordered nonunique = (1.5,7);
        attribute maximumIndividualWaveM : Real = 4;
        attribute pickupDelayHours : Real = 2;
        metadata rationale : ModelingMetadata::Rationale { text = "Design stress allocations, not climate return levels. Apply for the longest modeled casualty transit under the forecast-conditioned current field plus 2 h arranged pickup delay. Require launch logistics capable of this pickup delay; otherwise use the longer declared delay and re-evaluate flotation, retention and energy. Operational waves use Hs <= 1.5 m, Tp 1.5-5 s and an explicit 3 m individual-wave case. Recovery uses Hs <= 2 m, Tp 1.5-7 s and a 4 m individual-wave case. No independent-maxima probability is claimed. Ice, dam transit and surf-zone launch remain outside scope."; }
    }
    calc def RecoveryExposureHours {
        in transitHours : Real;
        in pickupHours : Real;
        return hours : Real = transitHours + pickupHours;
    }
    analysis FetchSensitivity {
        out attribute windsMps : Real [9] ordered nonunique = (6,6,6,10,10,10,15,15,15);
        out attribute fetchesM : Real [9] ordered nonunique = (3000,8000,15000,3000,8000,15000,3000,8000,15000);
        out attribute heightsM : Real [9] ordered nonunique = (1..9)->ControlFunctions::collect {
            in i : Integer; MarineSurface::FetchSea((windsMps#(i),fetchesM#(i),9.80665))#(1) };
        out attribute periodsSeconds : Real [9] ordered nonunique = (1..9)->ControlFunctions::collect {
            in i : Integer; MarineSurface::FetchSea((windsMps#(i),fetchesM#(i),9.80665))#(2) };
    }
    dependency windBasis from proposed to BlueDogRequirements::gorgeWind;
    dependency waveBasis from proposed to BlueDogRequirements::gorgeWaves;
    dependency currentBasis from proposed to BlueDogRequirements::gorgeCurrent;
    dependency launchContext from proposed to GorgeChallenge::forecastAdmission;
    dependency recoveryContext from proposed to GorgeChallenge::courseRecoveryReserve;
}

package BlueDogIntegratedCandidate {
    private import ScalarValues::*;
    doc /* Current working integration candidate. A refined IC-01-scale vessel is the intended first physical build.
     * Allocations are not selected catalog equipment or measured performance.
     * Independent recovery includes separate power, thrust, navigation and observation paths.
     * Every capability and independence claim requires configuration-specific physical evidence. */
    alias hypothesis for BlueDogIC01::integration;
    analysis Inputs {
        out attribute identifier : String = hypothesis.identifier;
        out attribute independentRecoveryAssumed : Boolean = hypothesis.independentRecoveryAssumed;
        out attribute parameterNames : String [2] ordered nonunique = ("electronicsW","fixedEquipmentKg");
        out attribute parameterValues : Real [2] ordered nonunique = (hypothesis.electronicsW,hypothesis.fixedEquipmentKg);
        out attribute designNames : String [29] ordered nonunique = BlueDogCoupledSizing::Inputs.designNames;
        out attribute designValues : Real [29] ordered nonunique = MarineDesign::DesignVector(BlueDogIC01::design);
        out attribute recoveryCapability : Real [7] ordered nonunique = (hypothesis.recoverySpeedMps,hypothesis.recoveryMotorW,hypothesis.recoveryEssentialW,hypothesis.recoveryUncertainty,hypothesis.arrivalAllowanceWh,hypothesis.invertedSpeedMps,hypothesis.invertedMotorW);
        out attribute recoveryDepartureWh : Real = hypothesis.recoveryDepartureWh;
        out attribute recoveryNameplateWh : Real = hypothesis.recoveryBatteryWh;
        out attribute recoveryStandbyW : Real = hypothesis.recoveryStandbyW;
        out attribute planningHorizonSeconds : Real = hypothesis.planningHorizonS;
        out attribute controlPeriodSeconds : Real = hypothesis.assessmentS;
        out attribute commandLatencySeconds : Real = hypothesis.commandS;
        out attribute maneuverSeconds : Real = hypothesis.maneuverS;
        out attribute minimumSailingSpeedMps : Real = hypothesis.minimumSailingSpeedMps;
        out attribute depowerPenaltyM : Real = hypothesis.depowerPenaltyM;
        out attribute crossTrackWeight : Real = hypothesis.crossTrackWeight;
        out attribute maneuverPenaltyM : Real = hypothesis.maneuverPenaltyM;
        out attribute sensorRangeM : Real = hypothesis.sensorRangeM;
        out attribute weedRangeM : Real = hypothesis.weedRangeM;
        out attribute sensorLatencyS : Real = hypothesis.sensorLatencyS;
        out attribute horizonS : Real = 14400;
        out attribute seeds : Integer [2] ordered nonunique = (17,29);
    }
    requirement def VirtualClosure {
        subject candidate;
        in attribute sizingPass : Boolean;
        in attribute nominalPass : Boolean;
        in attribute encountersPass : Boolean;
        in attribute recoveryPass : Boolean;
        in attribute energyPass : Boolean;
        in attribute timingPass : Boolean;
        in attribute assumptionsRecorded : Boolean;
        require constraint { sizingPass and nominalPass and encountersPass and recoveryPass and energyPass and timingPass and assumptionsRecorded }
    }
    calc def RecoveryBankAfterExposure {
        in exposureHours : Real;
        return remainingWh : Real = hypothesis.recoveryDepartureWh-hypothesis.recoveryStandbyW*exposureHours;
    }
    analysis def RecoveryScreen {
        subject candidate : MarineDesign::Design = BlueDogIC01::design;
        in attribute exposureHours : Real;
        in attribute distanceM : Real;
        in attribute alongCurrentMps : Real;
        in attribute crossCurrentMps : Real;
        in attribute inverted : Boolean;
        out attribute configurationApplicable : Boolean = candidate == BlueDogIC01::design;
        assert constraint configurationApplicability { configurationApplicable }
        assert constraint inputDomain { exposureHours >= 0 and distanceM >= 0 }
        attribute speedMps : Real = if inverted ? hypothesis.invertedSpeedMps else hypothesis.recoverySpeedMps;
        attribute motorW : Real = if inverted ? hypothesis.invertedMotorW else hypothesis.recoveryMotorW;
        attribute segment : Real [4] ordered nonunique = MarineRecovery::Segment((distanceM,speedMps,alongCurrentMps,crossCurrentMps,motorW,hypothesis.recoveryEssentialW,hypothesis.recoveryUncertainty));
        out attribute configurationId : String = hypothesis.identifier;
        out attribute mainNameplateWh : Real = BlueDogIC01::design.battery_Wh;
        out attribute independentNameplateWh : Real = hypothesis.recoveryBatteryWh;
        out attribute remainingWh : Real = RecoveryBankAfterExposure(exposureHours);
        out attribute groundSpeedMps : Real = segment#(2);
        out attribute transitSeconds : Real = segment#(3);
        out attribute requiredWh : Real = segment#(4)+hypothesis.arrivalAllowanceWh;
        out attribute routeFeasible : Boolean = segment#(1) == 1;
        out attribute reserveFits : Boolean = configurationApplicable and routeFeasible and remainingWh >= requiredWh;
        out attribute physicalQualification : Boolean = false;
        doc /* Conditional battery-side recovery arithmetic scoped to IC-01 only.
         * The native applicability assertion rejects an alternate runtime subject.
         * It does not establish an available safe approach, shore capture, thrust,
         * casualty survivability or physical qualification. Infeasible current
         * reports routeFeasible=false, never zero-energy recovery success. */
    }
    analysis IC01RecoveryIllustration : RecoveryScreen {
        subject :>> candidate;
        in attribute :>> exposureHours = Inputs.horizonS/3600;
        in attribute :>> distanceM = 600;
        in attribute :>> alongCurrentMps = -BlueDogMissionSimulation::weatherHypothesis.currentMps;
        in attribute :>> crossCurrentMps = 0;
        in attribute :>> inverted = false;
        doc /* Synthetic 600 m reach and four-hour exposure, matching the bounded
         * integration scenario scale; not the Gorge course or a required limit. */
    }
    analysis IC01InvertedRecoveryIllustration : RecoveryScreen {
        subject :>> candidate;
        in attribute :>> exposureHours = Inputs.horizonS/3600;
        in attribute :>> distanceM = 600;
        in attribute :>> alongCurrentMps = -BlueDogMissionSimulation::weatherHypothesis.currentMps;
        in attribute :>> crossCurrentMps = 0;
        in attribute :>> inverted = true;
    }
    analysis IC01NoRecoveryAuthority : RecoveryScreen {
        subject :>> candidate;
        in attribute :>> exposureHours = Inputs.horizonS/3600;
        in attribute :>> distanceM = 600;
        in attribute :>> alongCurrentMps = -hypothesis.recoverySpeedMps;
        in attribute :>> crossCurrentMps = 0;
        in attribute :>> inverted = false;
        doc /* Adverse arithmetic control: opposing current equals allocated
         * through-water speed, so no upstream route is credited. */
    }
    dependency recoveryReserveBasis from RecoveryScreen to BlueDogRequirements::recoveryEnergy;
    dependency recoveryConfiguration from RecoveryScreen to BlueDogIC01::design;
    dependency sizing from Inputs to BlueDogCoupledSizing::Inputs;
    dependency sensing from Inputs to BlueDogRequirements::trafficSafety;
    dependency recovery from Inputs to GorgeChallenge::autonomousShoreRecovery;
    dependency energy from Inputs to BlueDogRequirements::lowEnergyRecovery;
}

package BlueDogLocationTraffic { doc /* Desktop traffic assessment, 2026-10-16. Named sectors are survey scopes, not surveyed polygons or measured rates. No accepted departure window. Site evidence supports activities; conflict mechanisms and priority are engineering judgments. Existing mission actors remain scripted geometric proxies, not reactive wind-sport simulation.*/ private import ScalarValues::*;
    part policy {
        attribute sourceRegister : String = "evidence/traffic/2026-10-16-location-review/sources.json";
        attribute rateEvidenceAvailable : Boolean = false;
        attribute acceptedWindow : Boolean = false;
        attribute geometryStatus : String = "Survey WGS84 launch, riding, fall/relaunch and approach polygons; intersect both route legs and casualty routes. Include connecting reaches. Launch points do not bound riding areas.";
        attribute timingPolicy : String = "Review earliest entry through latest exit for each sector/class/condition on both legs, waiting and recovery. Use a common UTC epoch; retain local date/time and DST offset. Delay beyond the reviewed window requires reassessment.";
        attribute cooperationPolicy : String = "No probability credit for rider avoidance. Exercise timely, delayed, absent and failed response including falls. Predictable stand-on behavior still requires collision intervention.";
        attribute heatmapPolicy : String = "No Strava map sampled here. Global/Weekly/Night heatmaps may locate surveys, not calibrate hourly rates or prove absence. Personal date filtering is not a public hourly dataset.";
        attribute legalPolicy : String = "Apply Inland Rules and reviewed local restrictions; separate sailing category from speed/consequence. Exercise overtaking, tack, windward/leeward and failed give-way response. Autonomy and small size confer no restricted-maneuverability privilege. A shore launch prohibition does not imply absence offshore.";
    }
    part bingen {
        attribute location : String = "Bingen launch and departure/finish approaches";
        attribute basis : String = "Port-operated ramp/harbor and buoy-39 gate.";
        attribute hazards : String = "Launch traffic and low targets near departure, return and retrieval; wind-sport use unmeasured.";
        attribute nextInvestigation : String = "Count both approaches; distinguish ramp traffic from scored gate and survey waiting/capture.";
        attribute source : String = "Bingen port; TransGorgeCourse::east";
        attribute priority : String = "High: launch/retrieval";
        attribute status : String = "Open: no surveyed traffic footprint, calibrated rate or accepted window";
        attribute accepted : Boolean = false;
    }
    part bridge {
        attribute location : String = "Hood River bridge and White Salmon approaches";
        attribute basis : String = "Both legs use lift span; course records temporary works exclusion.";
        attribute hazards : String = "Confined passing, commercial traffic and occluded emergence; avoiding riders may conflict with span/works limits.";
        attribute nextInvestigation : String = "Review current notices, geometry and crossing opportunities without impeding commercial passage.";
        attribute source : String = "TransGorgeCourse::bridgePassage; TransGorgeCourse::temporaryWorks";
        attribute priority : String = "High: constrained passage";
        attribute status : String = "Open: no surveyed traffic footprint, calibrated rate or accepted window";
        attribute accepted : Boolean = false;
    }
    part hoodRiver {
        attribute location : String = "Hood River Event Site, sandbar, Hook and waterfront";
        attribute basis : String = "Port documents windsurfing, limited kiteboarding and mixed nonmotorized access.";
        attribute hazards : String = "Repeated crossings, learners, falls and launch/landing; shore-use boundaries are not riding footprints.";
        attribute nextInvestigation : String = "Survey offshore/cross-river tracks and events by wind/daylight; compare offsets without shifting risk to commercial passage.";
        attribute source : String = "Hood River waterfront; events";
        attribute priority : String = "High: documented mixed use";
        attribute status : String = "Open: no surveyed traffic footprint, calibrated rate or accepted window";
        attribute accepted : Boolean = false;
    }
    part hatchery {
        attribute location : String = "Spring Creek Hatchery and Swell City";
        attribute basis : String = "State park documents windsurfing/kiteboarding; CGW2 identifies windsurfer/winger access at Swell City.";
        attribute hazards : String = "Turns in swell, occluded fallen riders and overlapping passage/recovery exposure.";
        attribute nextInvestigation : String = "Observe both banks/offshore under west/east winds separately; assess recovery entry independently.";
        attribute source : String = "Spring Creek park; CGW2 Swell City";
        attribute priority : String = "High: wind sports/recovery overlap";
        attribute status : String = "Open: no surveyed traffic footprint, calibrated rate or accepted window";
        attribute accepted : Boolean = false;
    }
    part viento {
        attribute location : String = "Viento river access and adjacent reach";
        attribute basis : String = "Oregon State Parks documents river access and windsurfing.";
        attribute hazards : String = "Launch/fall areas and moving groups; downwind route extent remains a survey hypothesis.";
        attribute nextInvestigation : String = "Survey along-river and cross-river traffic, south-bank recovery and wind-conditioned arrival.";
        attribute source : String = "Viento park";
        attribute priority : String = "High: documented use; extent unknown";
        attribute status : String = "Open: no surveyed traffic footprint, calibrated rate or accepted window";
        attribute accepted : Boolean = false;
    }
    part homeValley {
        attribute location : String = "Home Valley / Wind River and Drano approaches";
        attribute basis : String = "Existing site review identifies recreation, fishing and entrance conflicts.";
        attribute hazards : String = "Mixed users; changing recovery destination can introduce unassessed approach exposure.";
        attribute nextInvestigation : String = "Map/count approaches separately; retain Drano default exclusion and verify Home Valley access.";
        attribute source : String = "BlueDogRecoverySiteReview::homeValley; BlueDogRecoverySiteReview::drano";
        attribute priority : String = "High: recovery uncertainty";
        attribute status : String = "Open: no surveyed traffic footprint, calibrated rate or accepted window";
        attribute accepted : Boolean = false;
    }
    part stevenson {
        attribute location : String = "Stevenson Bob's Beach, East Point and buoy-16 approaches";
        attribute basis : String = "Port documents windsurfing at Bob's Beach and directs kiteboarding to East Point.";
        attribute hazards : String = "Riding may intersect the turn and recovery. Bob's Beach launch prohibition does not exclude kiters offshore.";
        attribute nextInvestigation : String = "Survey windsurf/wing/kite tracks, rounding and ramp traffic; compare east/west wind and seasonal retrieval access.";
        attribute source : String = "Bob's Beach; East Point; TransGorgeCourse::west";
        attribute priority : String = "High: turn/recovery overlap";
        attribute status : String = "Open: no surveyed traffic footprint, calibrated rate or accepted window";
        attribute accepted : Boolean = false;
    }
    part connecting {
        attribute location : String = "Remaining connecting reaches on both legs";
        attribute basis : String = "Course connects sectors; no complete traffic census here.";
        attribute hazards : String = "Mobile riders, boats and people may occur away from launch sites. Sparse heat is not absence.";
        attribute nextInvestigation : String = "Bound background exposure on both legs, waiting and recovery; hotspot-only coverage cannot admit a mission.";
        attribute source : String = "TransGorgeCourse; field evidence pending";
        attribute priority : String = "Unresolved: complete coverage required";
        attribute status : String = "Open: no surveyed traffic footprint, calibrated rate or accepted window";
        attribute accepted : Boolean = false;
    }
    part windsurfCrossing {
        attribute targetClass : String = "windsurfer";
        attribute scenario : String = "Crossing on either tack, overtaking, abrupt tack/gybe";
        attribute extent : String = "Rider, board, mast and sail; fallen sail and separated person";
        attribute criterion : String = "Exercise sailing roles and unknown tack with timely/delayed/no rider response. Bound speed and turn rate from evidence; do not inherit generic 4 m/s.";
        attribute evidenceStatus : String = "Planned hazard case; no measured response or reactive simulation validation";
    }
    part wingfoilTurn {
        attribute targetClass : String = "wingfoiler";
        attribute scenario : String = "Fast crossing/overtaking followed by turn or fall";
        attribute extent : String = "Rider, board, underwater foil, handheld wing and leash";
        attribute criterion : String = "Retain foil swept volume. Fall transitions to person-in-water plus equipment; lost upright detection is not disappearance.";
        attribute evidenceStatus : String = "Planned hazard case; no measured response or reactive simulation validation";
    }
    part kiteSweep {
        attribute targetClass : String = "kiter";
        attribute scenario : String = "Crossing, jump/landing, crash and relaunch";
        attribute extent : String = "Rider, board/foil, kite and taut/slack line sweep";
        attribute criterion : String = "Track aerial, surface and underwater occupied volume. Board rectangle alone cannot qualify clearance; no assumed rider avoidance.";
        attribute evidenceStatus : String = "Planned hazard case; no measured response or reactive simulation validation";
    }
    part fallenRider {
        attribute targetClass : String = "personInWater";
        attribute scenario : String = "Fall during initially safe predicted pass";
        attribute extent : String = "Person and separately drifting equipment";
        attribute criterion : String = "Preserve objects/uncertainty until separation resolves; assess injury, entanglement and secondary immersion. Empty-looking board is not occupancy evidence.";
        attribute evidenceStatus : String = "Planned hazard case; no measured response or reactive simulation validation";
    }
    part groupEncounter {
        attribute targetClass : String = "unclassified";
        attribute scenario : String = "Several riders turn or fall near confined passage";
        attribute extent : String = "Union of plausible riders/equipment with track-association uncertainty";
        attribute criterion : String = "Exercise track swaps, occlusion and no safe sailing maneuver. Check abort/recovery against remaining traffic and commercial passage.";
        attribute evidenceStatus : String = "Planned hazard case; no measured response or reactive simulation validation";
    }
    part windowOverrun {
        attribute targetClass : String = "unclassified";
        attribute scenario : String = "Outbound fits quiet window; delayed return/recovery does not";
        attribute extent : String = "Whole route exposure including waiting and recovery";
        attribute criterion : String = "Reject unsupported conditions. Shift departure, route or waiting only with supported energy, sensing and recovery; darkness/calm is not automatically safer.";
        attribute evidenceStatus : String = "Planned hazard case; no measured response or reactive simulation validation";
    }
    analysis def WindowAssessment {
        doc /* One sector/class/condition visit. Rates count entries into the declared encounter envelope, not shore attendance. Upper rate bound must cover every condition/time in the interval; otherwise split rows. References and flags declare reviewed evidence; contents are not validated here. No Poisson assumption or collision-probability estimate. Passing a row cannot authorize launch.*/
        subject visit;
        in attribute sectorId : String;
        in attribute targetClass : String;
        in attribute earliestEntryUtcS : Real;
        in attribute latestExitUtcS : Real;
        in attribute evidenceStartUtcS : Real;
        in attribute evidenceEndUtcS : Real;
        in attribute encounterRateUpperPerHour : Real;
        in attribute reviewedExposureLimit : Real;
        in attribute geometryReviewRef : String;
        in attribute rateEvidenceRef : String;
        in attribute rateMethodReviewRef : String;
        in attribute exposureCriterionRef : String;
        in attribute conditionMatch : Boolean;
        in attribute classAllocationAccepted : Boolean;
        in attribute responseWithoutRiderCooperationSupported : Boolean;
        in attribute navigationObligationsSupported : Boolean;
        in attribute recoverySupported : Boolean;
        out attribute knownSector : Boolean = sectorId == "bingen" or sectorId == "bridge" or sectorId == "hoodRiver" or sectorId == "hatchery" or sectorId == "viento" or sectorId == "homeValley" or sectorId == "stevenson" or sectorId == "connecting";
        out attribute knownClass : Boolean = targetClass == "commercialTow" or targetClass == "fishingCraft" or targetClass == "fastCraft" or targetClass == "sailingCraft" or targetClass == "passengerVessel" or targetClass == "occupiedKayak" or targetClass == "occupiedSUP" or targetClass == "personInWater" or targetClass == "unoccupiedDriftingCraft" or targetClass == "windsurfer" or targetClass == "wingfoiler" or targetClass == "kiter" or targetClass == "unclassified";
        out attribute intervalSupported : Boolean = earliestEntryUtcS >= 0 and latestExitUtcS > earliestEntryUtcS and evidenceStartUtcS >= 0 and evidenceEndUtcS > evidenceStartUtcS and evidenceStartUtcS <= earliestEntryUtcS and evidenceEndUtcS >= latestExitUtcS;
        out attribute exposureSupported : Boolean = knownSector and knownClass and intervalSupported and conditionMatch and encounterRateUpperPerHour >= 0 and geometryReviewRef != "" and rateEvidenceRef != "" and rateMethodReviewRef != "";
        out attribute expectedEncountersUpper : Real = if exposureSupported ? encounterRateUpperPerHour*(latestExitUtcS-earliestEntryUtcS)/3600 else -1;
        out attribute exposureWithinCriterion : Boolean = exposureSupported and exposureCriterionRef != "" and reviewedExposureLimit >= 0 and expectedEncountersUpper <= reviewedExposureLimit;
        out attribute rowSupported : Boolean = exposureWithinCriterion and classAllocationAccepted and responseWithoutRiderCooperationSupported and navigationObligationsSupported and recoverySupported;
        out attribute launchAuthorized : Boolean = false;
        out attribute status : String = if not exposureSupported ? "Unsupported exposure estimate" else if not rowSupported ? "Exposure estimated; visit unsupported" else "Supplied visit criteria pass; complete mission admission still required";
    }
    part missionAdmission {
        doc /* Require a complete audited matrix of every traversed sector, admitted/uncertain class, condition and visit on outbound, return, waiting and recovery. Couple forecast, energy, current, night capability, surveyed capture and live reassessment. Review cumulative exposure over disjoint rows without double-counting actors; row limits do not establish voyage risk. No mission aggregator or launch release implemented here.*/
        attribute coverageReviewComplete : Boolean = false;
        attribute missionExposureAccepted : Boolean = false;
        attribute launchAuthorized : Boolean = false;
        attribute nextEvidence : String = "Independent time-stamped counts/tracks, observation effort/misses, wind/daylight, dates/events, speed/turn distributions, falls and rider response; surveyed polygons and arrival ensembles. Review upper bounds/confidence; zero observations do not imply zero rate.";
    }

    dependency allocationTrace from policy to BlueDogClassDetection::policy;
    dependency trafficSafety from policy to BlueDogRequirements::trafficSafety;
    dependency launchReview from missionAdmission to GorgeChallenge::forecastAdmission;
    dependency casualtyReview from missionAdmission to GorgeChallenge::courseRecoveryReserve;
    dependency courseScope from missionAdmission to TransGorgeCourse::policy;
    dependency windCases from policy to GorgeChallengeVerification::WindSportEncounterVerification;
    dependency windowCases from missionAdmission to GorgeChallengeVerification::LocationTrafficAdmissionVerification;
}
package BlueDogManeuverDynamics {
    private import ScalarValues::*;
    doc /* Optional low-order maneuver hypothesis. These coefficients are not
     * measured IC-01 properties. The model has bounded yaw rate and acceleration,
     * speed-dependent rudder authority, and maneuver speed loss; it has no yaw
     * inertia, wave excitation, roll coupling or calibrated stall dynamics.
     * Defaults are scenario inputs for sensitivity, never qualification evidence.
     */
    part hypothesis {
        attribute maxTurnRateDegS : Real = 6;
        attribute authoritySpeedMps : Real = 1;
        attribute minimumSteerSpeedMps : Real = 0.15;
        attribute accelerationMps2 : Real = 0.08;
        attribute decelerationMps2 : Real = 0.15;
        attribute turnSpeedRetention : Real = 0.8;
        attribute tackSpeedRetention : Real = 0.35;
        attribute gybeSpeedRetention : Real = 0.65;
        attribute recoverySpeedRetention : Real = 0.7;
    }
    analysis Defaults {
        out attribute maxTurnRateDegS : Real = hypothesis.maxTurnRateDegS;
        out attribute authoritySpeedMps : Real = hypothesis.authoritySpeedMps;
        out attribute minimumSteerSpeedMps : Real = hypothesis.minimumSteerSpeedMps;
        out attribute accelerationMps2 : Real = hypothesis.accelerationMps2;
        out attribute decelerationMps2 : Real = hypothesis.decelerationMps2;
        out attribute turnSpeedRetention : Real = hypothesis.turnSpeedRetention;
        out attribute tackSpeedRetention : Real = hypothesis.tackSpeedRetention;
        out attribute gybeSpeedRetention : Real = hypothesis.gybeSpeedRetention;
        out attribute recoverySpeedRetention : Real = hypothesis.recoverySpeedRetention;
    }
    analysis StudyInputs {
        out attribute names : String [6] ordered = ("ordinary_turn","tack","gybe","low_speed_authority","rudder_unavailable","recovery_turn");
        out attribute initialHeadingDeg : Real [6] ordered nonunique = (0,45,135,0,0,0);
        out attribute targetHeadingDeg : Real [6] ordered nonunique = (90,315,225,90,90,90);
        out attribute initialSpeedMps : Real [6] ordered nonunique = (1,1,1,0.1,1,1);
        out attribute targetSpeedMps : Real [6] ordered nonunique = (1,1,1,0.1,1,1);
        out attribute kinds : String [6] ordered nonunique = ("turn","tack","gybe","turn","turn","recovery");
        out attribute rudderFractions : Real [6] ordered nonunique = (1,1,1,1,0,1);
        out attribute horizonS : Real = 120;
        out attribute intervalsS : Real [2] ordered = (1,0.25);
        out attribute currentMps : Real [2] ordered = (0.3,0);
        metadata rationale : ModelingMetadata::Rationale { text = "Synthetic component trajectories with constant requested speed. Add the same 0.3 m/s eastward current externally; water-relative speed sets rudder authority. Tack and gybe labels prescribe loss hypotheses, not a resolved polar/roll model. Low-speed and unavailable-rudder cases may never finish; do not replace censoring with a finite maneuver bound."; }
    }
    action def Advance {
        in headingErrorDeg : Real;
        in speedMps : Real;
        in targetSpeedMps : Real;
        in intervalS : Real;
        in rudderFraction : Real;
        in speedRetention : Real;
        in maxTurnRateDegS : Real;
        in authoritySpeedMps : Real;
        in minimumSteerSpeedMps : Real;
        in accelerationMps2 : Real;
        in decelerationMps2 : Real;
        out speedNextMps : Real;
        out speedMeanMps : Real;
        out turnRateDegS : Real;
        out deltaHeadingDeg : Real;
        first start;
        then action advance {
            assign speedNextMps := if targetSpeedMps*speedRetention > speedMps ?
                RealFunctions::min(targetSpeedMps*speedRetention, speedMps+accelerationMps2*intervalS)
            else RealFunctions::max(targetSpeedMps*speedRetention, speedMps-decelerationMps2*intervalS);
            assign speedMeanMps := (speedMps+speedNextMps)/2;
            assign turnRateDegS := maxTurnRateDegS*rudderFraction*
                RealFunctions::min(1,RealFunctions::max(0,(speedMeanMps-minimumSteerSpeedMps)/(authoritySpeedMps-minimumSteerSpeedMps)));
            assign deltaHeadingDeg := if headingErrorDeg >= 0 ?
                RealFunctions::min(headingErrorDeg,turnRateDegS*intervalS)
            else -RealFunctions::min(-headingErrorDeg,turnRateDegS*intervalS);
        }
        then done;
    }
    dependency controlEvidence from hypothesis to BlueDogRequirements::trafficSafety;
}

package BlueDogMissionSimulation {
    private import ScalarValues::*;
    part scenarioPolicy {
        attribute stepSeconds : Real = 30;
        attribute controlPeriodSeconds : Real = 30;
        attribute horizonHours : Real = 240;
        attribute seed : Integer = 20261011;
        attribute ensembleCount : Integer = 32;
        attribute forecastSeconds : Real = 180;
        attribute routeLookaheadM : Real = 180;
        attribute maneuverSeconds : Real = 15;
        attribute gateApproachM : Real = 80;
        attribute completionDeadlineEnabled : Boolean = false;
        metadata rationale : ModelingMetadata::Rationale { text = "Numerical campaign settings, not challenge requirements. A run that reaches its horizon before finishing is censored, not a failed deadline. Seeded independent scenario streams permit reproducible paired design comparisons. Controller updates have their own fixed period; refining integration does not change the guidance policy or shorten maneuver delay. Repeat with smaller time steps and longer horizons before interpreting an ensemble."; }
    }
    part conceptualVessel {
        attribute batteryWh : Real = 500;
        attribute initialEnergyWh : Real = 500;
        attribute protectedReserveWh : Real = 60;
        attribute baseLoadW : Real = 5 + BlueDogWindEquipment::challenge.busPowerW;
        attribute maneuverEnergyWh : Real = 0.025;
        attribute solarPeakW : Real = 40;
        attribute solarEfficiency : Real = 0.85;
        attribute dischargeEfficiency : Real = 0.9;
        attribute beamM : Real = 0.5;
        attribute lengthM : Real = 1.2;
        attribute speedCapMps : Real = 3;
        attribute polarAnglesDeg : Real [7] ordered nonunique = (0,35,45,60,90,135,180);
        attribute speedWindRatios : Real [7] ordered nonunique = (0,0,0.28,0.36,0.45,0.38,0.30);
        metadata rationale : ModelingMetadata::Rationale { text = "Declared conceptual boat used to exercise mission logic before detailed-design convergence. These speed ratios and energy allowances are hypotheses, not VSP results, measured polars or the optimized Blue Dog design. Replace the performance provider and equipment budget with a named, correlated configuration without changing course or verdict logic. Sensor power uses the current wired installation roll-up."; }
        metadata issue : ModelingMetadata::Issue { text = "No physical performance or energy acceptance attaches to this configuration. The 60 Wh reserve is a scenario allocation; final reserve must use RecoveryReserveDemand with measured installed recovery and essential loads. Peak power, turning dynamics, capsize and wave response require higher-fidelity providers."; }
    }
    part weatherHypothesis {
        attribute initialWindFromDeg : Real = 270;
        attribute meanWindMps : Real = 7;
        attribute currentMps : Real = 0.4;
        attribute meanRegimeHours : Real = 36;
        attribute eastRegimeProbability : Real = 0.2;
        attribute hourlyPersistence : Real = 0.85;
        attribute windInnovationMps : Real = 0.8;
        attribute minimumCloudTransmission : Real = 0.15;
        attribute nominalCloudTransmission : Real = 0.8;
        attribute cloudDisturbanceCoefficient : Real = 0.08;
        attribute currentDisturbanceCoefficient : Real = 0.03;
        attribute sunriseHour : Real = 6;
        attribute sunsetHour : Real = 18;
        attribute departureHour : Real = 8;
        metadata rationale : ModelingMetadata::Rationale { text = "Synthetic weather-window sensitivity generator. Begin in a westerly window, retain temporally persistent regimes, and couple cloud, wind perturbations and current in each realization. The east probability and persistence are uncalibrated hypotheses, not a forecast-conditioned Gorge completion probability. NOAA station evidence in BlueDogWeather motivates regimes but does not justify these numeric weights."; }
    }
    part trafficHypothesis {
        attribute names : String [5] ordered = ("commercial tow", "fishing craft", "recreational powerboat", "sailing vessel", "passenger vessel");
        attribute arrivalsPerHour : Real [5] ordered nonunique = (0.1,0.5,0.5,0.3,0.05);
        attribute speedsMps : Real [5] ordered nonunique = (3.5,1.5,10,2,4);
        attribute lengthsM : Real [5] ordered nonunique = (180,6,7,8,100);
        attribute beamsM : Real [5] ordered nonunique = (24,2.5,2.5,3,18);
        attribute separationM : Real [5] ordered nonunique = (50,20,30,20,50);
        metadata rationale : ModelingMetadata::Rationale { text = "Initial encounter hypotheses for the finite mission, not measured traffic distributions. USACE identifies tow blind spots; the commercial footprint includes tug and barges rather than a single AIS point. The archived regional VesselFinder snapshot includes passenger hulls up to 100 by 18 m but does not establish arrival frequency. Fishing/recreation are supported by the Oregon boating guide. Rates, speeds and separations are scenario allocations; calibrate with time-stamped observations before claiming probability. See evidence/course/2026-10-11/sources.json. Small craft may have no AIS. Add crossing, overtaking, anchored/drifting fishing and changing-course skiing cases independently of the random transit generator."; }
        metadata issue : ModelingMetadata::Issue { text = "Separation domains are analysis screens, not statutory stand-offs or proof of Navigation Rules compliance. Fishing-vessel privilege depends on actual gear restriction, not the actor's label. Seasonal/daytime concentration, wakes, hidden targets and maneuver response require explicit scenario coverage."; }
    }
    analysis Inputs {
        out attribute gateNames : String [5] ordered nonunique = TransGorgeCourse::policy.gateNames;
        out attribute gateDirections : Integer [5] ordered nonunique = TransGorgeCourse::policy.gateDirections;
        out attribute controlPeriodSeconds : Real = scenarioPolicy.controlPeriodSeconds;
        out attribute commandLatencySeconds : Real = BlueDogEncounterReview::criteria.commandSeconds;
        out attribute continueAfterAbort : Boolean = true;
        out attribute gateApproachM : Real = scenarioPolicy.gateApproachM;
        out attribute time : Real [6] ordered nonunique = (scenarioPolicy.stepSeconds,scenarioPolicy.horizonHours,scenarioPolicy.forecastSeconds,scenarioPolicy.routeLookaheadM,scenarioPolicy.maneuverSeconds,scenarioPolicy.seed);
        out attribute energy : Real [8] ordered nonunique = (conceptualVessel.batteryWh,conceptualVessel.initialEnergyWh,conceptualVessel.protectedReserveWh,conceptualVessel.baseLoadW,conceptualVessel.maneuverEnergyWh,conceptualVessel.solarPeakW,conceptualVessel.solarEfficiency,conceptualVessel.dischargeEfficiency);
        out attribute dimensions : Real [3] ordered nonunique = (conceptualVessel.lengthM,conceptualVessel.beamM,conceptualVessel.speedCapMps);
        out attribute angles : Real [7] ordered nonunique = conceptualVessel.polarAnglesDeg;
        out attribute speedRatios : Real [7] ordered nonunique = conceptualVessel.speedWindRatios;
        out attribute weather : Real [14] ordered nonunique = (weatherHypothesis.initialWindFromDeg,weatherHypothesis.meanWindMps,weatherHypothesis.currentMps,weatherHypothesis.meanRegimeHours,weatherHypothesis.eastRegimeProbability,weatherHypothesis.hourlyPersistence,weatherHypothesis.windInnovationMps,weatherHypothesis.minimumCloudTransmission,weatherHypothesis.nominalCloudTransmission,weatherHypothesis.cloudDisturbanceCoefficient,weatherHypothesis.currentDisturbanceCoefficient,weatherHypothesis.sunriseHour,weatherHypothesis.sunsetHour,weatherHypothesis.departureHour);
        out attribute trafficNames : String [5] ordered = trafficHypothesis.names;
        out attribute trafficRates : Real [5] ordered nonunique = trafficHypothesis.arrivalsPerHour;
        out attribute trafficSpeeds : Real [5] ordered nonunique = trafficHypothesis.speedsMps;
        out attribute trafficLengths : Real [5] ordered nonunique = trafficHypothesis.lengthsM;
        out attribute trafficBeams : Real [5] ordered nonunique = trafficHypothesis.beamsM;
        out attribute trafficSeparation : Real [5] ordered nonunique = trafficHypothesis.separationM;
    }
    dependency course from Inputs to GorgeChallenge::courseCompletion;
    dependency autonomy from Inputs to GorgeChallenge::unassistedAttempt;
    dependency sailing from Inputs to GorgeChallenge::sailingPropulsion;
    dependency traffic from Inputs to GorgeChallenge::trafficCoexistence;
    dependency navigation from Inputs to GorgeChallenge::navigationRules;
    dependency reserve from Inputs to BlueDogRequirements::lowEnergyRecovery;
    dependency finiteEndurance from Inputs to BlueDogRequirements::multiDayEndurance;
    calc def MissionOutcome {
        in orderedCourseComplete : Boolean;
        in intervention : Boolean;
        in motorUsed : Boolean;
        in safetyViolation : Boolean;
        in executionStopped : Boolean;
        in reserveProtected : Boolean;
        in horizonReached : Boolean;
        in safetyAbort : Boolean;
        return outcome : String;
        if safetyViolation ? "safety_violation"
        else if intervention or motorUsed or safetyAbort ? "disqualified"
        else if executionStopped or not reserveProtected ? "incomplete"
        else if orderedCourseComplete ? "qualified_completion"
        else if horizonReached ? "censored"
        else "incomplete"
    }
    dependency simulatedCourseCriterion from MissionOutcome to GorgeChallenge::courseCompletion;
    dependency simulatedAutonomyCriterion from MissionOutcome to GorgeChallenge::unassistedAttempt;
    dependency simulatedPropulsionCriterion from MissionOutcome to GorgeChallenge::sailingPropulsion;
    dependency simulatedCollisionCriterion from MissionOutcome to GorgeChallenge::trafficCoexistence;
    dependency simulatedReserveCriterion from MissionOutcome to BlueDogRequirements::lowEnergyRecovery;
    comment acceptanceScope /* MissionOutcome classifies observed simulation facts. It does not establish complete navigation-rule compliance, sensor credibility, launch authorization or physical qualification. Python computes continuous geometry and dynamics; this calculation owns the outcome precedence. */
}

package BlueDogNavigationController { doc /* Mission integration policy for supplied Inland pair assessments. Numerical thresholds below are engineering hypotheses, not statutory interpretations or physically validated limits.*/ private import ScalarValues::*; part context;
    analysis def Policy {
        subject encounter;
        out attribute headingToleranceDeg : Real = 2.0;
        out attribute speedToleranceMps : Real = 0.05;
        out attribute substantialTurnDeg : Real = 15.0;
        out attribute bearingUncertaintyDeg : Real = 10.0;
        out attribute clearanceReleaseMultiplier : Real = 2.0;
    }
    analysis def Candidate {
        doc /* Filters a geometrically feasible proposal using the native pair response. Hold-course/speed tolerances and substantial-turn threshold are declared hypotheses. No supported candidate causes a navigation abort, not an inferred lawful emergency departure. Recovery is separately unassessed.*/
        subject encounter;
        in attribute relevant : Boolean;
        in attribute supported : Boolean;
        in attribute candidateClear : Boolean;
        in attribute heldClear : Boolean;
        in attribute holdsCourseSpeed : Boolean;
        in attribute substantialChange : Boolean;
        in attribute missingTrackedDuty : Boolean;
        in attribute response : String;
        out attribute allowed : Boolean = not missingTrackedDuty and (if not relevant ? true else supported and candidateClear and (continuationSupported or (if response == "holdCourseSpeed" ? holdsCourseSpeed else if response == "mayAct" ? holdsCourseSpeed or substantialChange else if response == "keepClear" or response == "shallAct" ? (heldClear and holdsCourseSpeed) or substantialChange else response == "monitor")));
        out attribute completeComplianceEstablished : Boolean = false;
        in attribute continuationSupported : Boolean;
    }
    analysis def Geometry {
        doc /* Geometry-to-assessed-fact hypotheses. Past-and-clear requires an observed opening track beyond twice the protected envelope and no forecast conflict. Track loss never meets this condition. Substantial action here only recognizes a heading change; speed-only maneuvers need a separate validated criterion.*/
        subject encounter;
        in attribute rangeM : Real;
        in attribute closingMps : Real;
        in attribute protectedRadiusM : Real;
        in attribute releaseMultiplier : Real;
        in attribute headingChangeDeg : Real;
        in attribute speedChangeMps : Real;
        in attribute headingToleranceDeg : Real;
        in attribute speedToleranceMps : Real;
        in attribute substantialTurnDeg : Real;
        in attribute heldConflict : Boolean;
        in attribute headingKnown : Boolean;
        in attribute trackAdequate : Boolean;
        out attribute pastAndClear : Boolean = trackAdequate and not heldConflict and closingMps < 0 and rangeM > protectedRadiusM * releaseMultiplier;
        out attribute holdsCourseSpeed : Boolean = headingKnown and headingChangeDeg <= headingToleranceDeg and speedChangeMps <= speedToleranceMps;
        out attribute substantialChange : Boolean = headingKnown and headingChangeDeg >= substantialTurnDeg;
    }
    analysis def Context {
        doc /* This controller integration is restricted to the assessed synthetic clear-visibility, non-channel context. Other contexts require a separate controller implementation, even without observed traffic. This scope gate is not a general legal prohibition.*/
        subject encounter;
        in attribute inlandProfile : String;
        in attribute channelContext : String;
        in attribute restrictedVisibility : String;
        in attribute specialCircumstances : String;
        out attribute supported : Boolean = inlandProfile == "yes" and channelContext == "no" and restrictedVisibility == "no" and specialCircumstances == "no";
    }
}
package BlueDogPassageExposure {
    private import ScalarValues::*;
    analysis Contours {
        out attribute hours : Real [15] ordered = (12,18,24,30,36,42,48,54,60,66,72,78,84,90,96);
        out attribute rate99 : Real [15] ordered nonunique = hours->ControlFunctions::collect { in h : Real; MarineReliability::EqualSurvivalRate(0.99,h) };
        out attribute rate95 : Real [15] ordered nonunique = hours->ControlFunctions::collect { in h : Real; MarineReliability::EqualSurvivalRate(0.95,h) };
        out attribute rate90 : Real [15] ordered nonunique = hours->ControlFunctions::collect { in h : Real; MarineReliability::EqualSurvivalRate(0.90,h) };
        out attribute rate80 : Real [15] ordered nonunique = hours->ControlFunctions::collect { in h : Real; MarineReliability::EqualSurvivalRate(0.80,h) };
        out attribute exampleHours : Real [2] ordered = (60,30);
        out attribute exampleRates : Real [2] ordered = (0.001,0.0015);
        out attribute slowerSurvival : Real = MarineReliability::ConstantHazardSurvival(exampleRates#(1),exampleHours#(1));
        out attribute fasterSurvival : Real = MarineReliability::ConstantHazardSurvival(exampleRates#(2),exampleHours#(2));
        out attribute fasterWins : Boolean = fasterSurvival > slowerSurvival;
        metadata rationale : ModelingMetadata::Rationale { text = "Illustrative sensitivity for the finite Gorge mission: hourly critical failure rate may rise if total accumulated hazard falls. Points are hypothetical, not displacement/planing predictions or measured Blue Dog rates. Contours describe conditional hardware survival only; route completion, holds, weather and operational failures require joint trajectory evaluation."; }
    }
    dependency missionSelection from Contours to BlueDogMissionScope::current;
    dependency exposureCriterion from Contours to BlueDogRequirements::passageDuration;
    dependency survivalCriterion from Contours to BlueDogRequirements::missionSuccessProbability;
    dependency failureMechanisms from Contours to BlueDogDFMEA::starter;
}

package BlueDogSailing {
    private import ScalarValues::*;
    private import ISQ::*;
    private import SI::*;
    doc /* Inverse performance demand and a wave-speed reference, not a VPP.
     * The route is aligned with the wind axis; symmetric tacks/gybes cancel
     * cross-track motion, with no cross-current. TWA uses water-relative true
     * wind. Leeway increases the absolute track angle away from the wind.
     * A uniform maneuver factor reduces average water VMG; current continues
     * throughout. Environmental retention is a through-water speed factor here.
     * Weather holds are separate in VoyageProfile.
     */
    calc def CourseProjection {
        in trueWindAngle : AngularMeasureValue;
        in leeway : AngularMeasureValue;
        in windward : Boolean;
        return projection : Real;
        (if windward ? 1 else -1) * TrigFunctions::cos((trueWindAngle + leeway) / (1 [rad]))
    }
    calc def RequiredPolarSpeed {
        in groundTarget : SpeedValue;
        in current : SpeedValue;
        in retention : Real;
        in maneuver : Real;
        in projection : Real;
        return speed : SpeedValue;
        if retention > 0 and retention <= 1 and maneuver > 0 and maneuver <= 1 and projection > 0 and projection <= 1 ?
            (if groundTarget > current ? (groundTarget - current) / (retention * maneuver * projection) else 0 [m/s])
        else 0 [m/s]
    }
    calc def WaveReferenceSpeed {
        in waterline : LengthValue;
        return speed : SpeedValue;
        if waterline > 0 [m] ? RealFunctions::sqrt(9.80665 * (waterline / (1 [m])) / (2 * TrigFunctions::pi)) * (1 [m/s]) else 0 [m/s]
    }
    calc def LengthFroude {
        in speed : SpeedValue;
        in waterline : LengthValue;
        return number : Real;
        if waterline > 0 [m] ? (speed / (1 [m/s])) / RealFunctions::sqrt(9.80665 * (waterline / (1 [m]))) else 0
    }
    calc def WaveReferenceLength {
        in speed : SpeedValue;
        return waterline : LengthValue;
        2 * TrigFunctions::pi * (speed / (1 [m/s])) * (speed / (1 [m/s])) / 9.80665 * (1 [m])
    }
    part def PolarLeg :> BlueDogReliability::SailingLeg {
        attribute label : String;
        attribute trueWindSpeed : SpeedValue;
        attribute trueWindAngle : AngularMeasureValue;
        attribute leeway : AngularMeasureValue;
        attribute windward : Boolean;
        attribute cleanPolarSpeed : SpeedValue;
        attribute maneuverRetention : Real;
        attribute waterlineLength : LengthValue;
        attribute allocatedTime : TimeValue;
        attribute minimumGroundVMG : SpeedValue;
        attribute polarEvidenceAccepted : Boolean;
        attribute hullEvidenceAccepted : Boolean;
        attribute projection : Real = CourseProjection(trueWindAngle, leeway, windward);
        attribute :>> waterVMG = cleanPolarSpeed * maneuverRetention * projection;
        attribute demandInputsValid : Boolean = distance > 0 [m] and trueWindSpeed > 0 [m/s] and
        trueWindAngle >= 0 [rad] and trueWindAngle <= TrigFunctions::pi * (1 [rad]) and
        leeway >= 0 [rad] and trueWindAngle + leeway <= TrigFunctions::pi * (1 [rad]) and
        projection > 0.000001 and projection <= 1 and retainedPerformance > 0 and retainedPerformance <= 1 and
        maneuverRetention > 0 and maneuverRetention <= 1 and waterlineLength > 0 [m] and allocatedTime > 0 [s] and
        minimumGroundVMG >= 0 [m/s];
        attribute timeTarget : SpeedValue = if allocatedTime > 0 [s] ? distance / allocatedTime else 0 [m/s];
        attribute requiredGroundVMG : SpeedValue = if timeTarget > minimumGroundVMG ? timeTarget else minimumGroundVMG;
        attribute requiredCleanPolar : SpeedValue = RequiredPolarSpeed(requiredGroundVMG, currentVMG, retainedPerformance, maneuverRetention, projection);
    }
    analysis def PolarDemandAndHullScreen {
        subject leg : PolarLeg;
        out attribute inputsValid : Boolean = leg.demandInputsValid and leg.cleanPolarSpeed > 0 [m/s];
        assert constraint validInputs { inputsValid }
        out attribute sampledWindSpeed : SpeedValue = leg.trueWindSpeed;
        out attribute requiredGroundVMG : SpeedValue = leg.requiredGroundVMG;
        out attribute requiredCleanPolarSpeed : SpeedValue = leg.requiredCleanPolar;
        out attribute requiredOperatingSpeed : SpeedValue = requiredCleanPolarSpeed * leg.retainedPerformance;
        out attribute requiredCleanKnots : Real = requiredCleanPolarSpeed / ((1852.0 / 3600.0) [m/s]);
        out attribute requiredSpeedWindRatio : Real = if inputsValid ? requiredCleanPolarSpeed / leg.trueWindSpeed else 0;
        out attribute candidateGroundVMG : SpeedValue = leg.groundVMG;
        out attribute candidateHours : Real = leg.travelTime / (3600 [s]);
        out attribute minimumProgressMet : Boolean = BlueDogRequirements::LegProgressCriterion((leg.groundVMG));
        out attribute allocatedDurationMet : Boolean = leg.valid and BlueDogRequirements::PassageDurationCriterion(leg.travelTime, leg.allocatedTime);
        out attribute waveReference : SpeedValue = WaveReferenceSpeed(leg.waterlineLength);
        out attribute requiredCleanFroude : Real = LengthFroude(requiredCleanPolarSpeed, leg.waterlineLength);
        out attribute requiredOperatingFroude : Real = LengthFroude(requiredOperatingSpeed, leg.waterlineLength);
        out attribute equivalentWaveLength : LengthValue = WaveReferenceLength(requiredCleanPolarSpeed);
        out attribute exceedsWaveReference : Boolean = requiredCleanPolarSpeed > waveReference;
        out attribute evidenceReady : Boolean = leg.polarEvidenceAccepted and leg.hullEvidenceAccepted;
        return modeledFeasible : Boolean = inputsValid and leg.valid and allocatedDurationMet;
        out attribute performanceSupported : Boolean = modeledFeasible and evidenceReady;
        objective feasibility { require constraint { modeledFeasible } }
    }
    part def PolarVoyageProfile :> BlueDogReliability::VoyageProfile {
        part :>> legs : PolarLeg [1..*] ordered;
        attribute allocatedDuration : TimeValue = NumericalFunctions::sum(legs.allocatedTime) + holdTime;
        attribute :>> profileEvidenceAccepted = legs->ControlFunctions::forAll { in leg : PolarLeg; leg.polarEvidenceAccepted and leg.hullEvidenceAccepted };
    }
    analysis def PolarVoyageAssessment {
        subject profile : PolarVoyageProfile;
        analysis cruise : BlueDogReliability::CruiseReliability { subject = profile; }
        out attribute allocationValid : Boolean = profile.valid and SequenceFunctions::size(profile.legs) > 0 and
        profile.legs->ControlFunctions::forAll { in leg : PolarLeg; leg.demandInputsValid and leg.cleanPolarSpeed > 0 [m/s] } and
        BlueDogRequirements::PassageDurationCriterion(profile.allocatedDuration, profile.qualifiedDuration);
        out attribute legBudgetsMet : Boolean = profile.legs->ControlFunctions::forAll { in leg : PolarLeg;
            leg.valid and BlueDogRequirements::PassageDurationCriterion(leg.travelTime, leg.allocatedTime) };
        out attribute allocatedHours : Real = profile.allocatedDuration / (3600 [s]);
        out attribute voyageHours : Real = cruise.voyageHours;
        out attribute groundSpeeds : SpeedValue [*] ordered nonunique = cruise.groundSpeeds;
        out attribute allowableRatePerHour : Real = cruise.allowableRatePerHour;
        out attribute evidenceReady : Boolean = cruise.evidenceReady;
        return modeledFeasible : Boolean = allocationValid and legBudgetsMet and cruise.modeledFeasible;
        out attribute voyageSupported : Boolean = modeledFeasible and cruise.reliabilitySupported;
        objective feasibility { require constraint { modeledFeasible } }
    }
    analysis def SailingSensitivity {
        subject leg : PolarLeg;
        assert constraint validInputs { leg.demandInputsValid and leg.leeway == 0 [rad] }
        out attribute referenceTwaDegrees : Real = TrigFunctions::deg(leg.trueWindAngle / (1 [rad]));
        out attribute groundTarget : SpeedValue = leg.requiredGroundVMG;
        out attribute alongCurrent : SpeedValue = leg.currentVMG;
        out attribute retainedPerformance : Real = leg.retainedPerformance;
        out attribute maneuverRetention : Real = leg.maneuverRetention;
        out attribute beatAngles : Real [*] ordered = (6..15)->ControlFunctions::collect { in i : Integer; i * 5.0 };
        out attribute runAngles : Real [*] ordered = (21..36)->ControlFunctions::collect { in i : Integer; i * 5.0 };
        out attribute beatSpeeds : SpeedValue [*] ordered nonunique = beatAngles->ControlFunctions::collect { in a : Real;
            RequiredPolarSpeed(leg.requiredGroundVMG, leg.currentVMG, leg.retainedPerformance, leg.maneuverRetention, CourseProjection(TrigFunctions::rad(a) * (1 [rad]), leg.leeway, true)) };
        out attribute runSpeeds : SpeedValue [*] ordered nonunique = runAngles->ControlFunctions::collect { in a : Real;
            RequiredPolarSpeed(leg.requiredGroundVMG, leg.currentVMG, leg.retainedPerformance, leg.maneuverRetention, CourseProjection(TrigFunctions::rad(a) * (1 [rad]), leg.leeway, false)) };
        out attribute waterlines : LengthValue [*] ordered = (2..16)->ControlFunctions::collect { in i : Integer; i * 0.25 [m] };
        out attribute waveSpeeds : SpeedValue [*] ordered = waterlines->ControlFunctions::collect { in length : LengthValue; WaveReferenceSpeed(length) };
        out attribute cleanDemand : SpeedValue = leg.requiredCleanPolar;
        out attribute operatingDemand : SpeedValue = leg.requiredCleanPolar * leg.retainedPerformance;
        return computed : Boolean = leg.demandInputsValid and leg.leeway == 0 [rad];
        objective consistency { require constraint { computed } }
    }
    dependency progressDemand from PolarDemandAndHullScreen to BlueDogRequirements::legProgress;
    dependency timeAllocation from PolarDemandAndHullScreen to BlueDogRequirements::passageDuration;
    dependency polarEvidence from PolarDemandAndHullScreen to BlueDogRequirements::cruiseEvidence;
    dependency currentBoundary from PolarDemandAndHullScreen to BlueDogRequirements::gorgeCurrent;
    dependency weedAllowance from PolarDemandAndHullScreen to BlueDogRequirements::submergedWeedPassage;
    dependency hullDecision from PolarDemandAndHullScreen to BlueDog::Architecture::HullAndRig;
    dependency cruiseIntegration from BlueDogReliability::CruiseReliability to PolarDemandAndHullScreen;
}

package RecoveryPropulsionTrade {
    private import ScalarValues::*;
    private import ISQ::*;
    private import SI::*;
    doc /* Preliminary axial actuator-disk analysis. Example inputs are illustrative,
     * not measured Blue Dog hardware. Negative axial inflow, crosswind, ventilation,
     * cavitation, weed drag and propeller/hull interactions are outside this model.
     */

    part comparisonBasis {
        doc /* The judgments below are engineering hypotheses to verify on the installed boat. No numerical score or weighting is assigned without measured performance and an agreed priority.

| Criterion / requirement | Submerged water propeller | Above-water air propeller | Evidence needed |
| --- | --- | --- | --- |
| Thrust versus energy, R-001/R-002 | Dense working fluid favors compact low-speed thrust; actual losses depend on diameter, pitch, immersion and installation | Lower density drives greater disk area or induced velocity for comparable static thrust; battery demand may dominate | Hull tow test, installed thrust/power curves and recovery run |
| Milfoil, N-053–N-056 | Blades, shaft and guard can wrap or collect stems; a duct/guard is not automatically weed-proof | Rotor avoids submerged stems while upright, but hull/keel/rudder can still anchor the boat in vegetation | Same patch and snag tests, including restart after blockage |
| Sailing drag and packaging | Submerged installation adds drag; folding/retracting concepts introduce moving parts and new failure modes | Adds windage, deck volume, possible sail interference and elevated mass | Coast/tow drag, wind-load and sail-clearance measurements |
| Capsize and waves, N-051/N-052 | Can ventilate or leave water while heeled; immersed motor/shaft sealing is central | Rotor can strike water, guard or rig during heel/capsize; restart while wet must be qualified | Heel clearances, disabled-rotor immersion, self-righting and post-capsize restart |
| Steering and reverse | Rudder-in-slipstream or steerable pod possible; reverse depends on selected propeller/drive | Air rudder, vectored thrust or differential thrust may be needed at low boat speed; ordinary air propellers are not assumed efficient in reverse | Low-speed turning, stopping and control-loss tests |
| Guarding and handling, S-003 | Contact hazard at launch/recovery; guards can collect weeds and add drag | Accessible high-speed rotor needs physical separation/guarding; larger guard increases windage and mass | Isolation timing, access assessment, guard deflection/clearance under loads |
| Corrosion and maintenance, N-042/P-003 | Continuous immersion, seals/bearings and dissimilar metals need attention | Less continuous immersion but still salt spray, condensation and capsize exposure | Exposure campaign and timed replacement |
| Wind sensitivity | Hull wind load still affects recovery; underwater inflow follows boat/current | Propeller inflow also changes directly with apparent wind and yaw | Installed testing across recovery wind headings |
| Cost and manufacturability | Waterproof drive hardware may add complexity; custom printed rotating blades are not assumed qualified | Hobby components may simplify prototyping, but marine protection and guards remain additional work | Actual BOM, mass, print jobs and supplier operating limits | */
        metadata rationale : ModelingMetadata::Rationale { text = "Retain water propulsion as the compact energy-focused reference and air propulsion as the submerged-rotor-fouling alternative. These are engineering hypotheses; installed evidence determines the choice."; }
    }
    dependency comparisonCriteria from comparisonBasis to RecoverySizing;
    part def Candidate :> BlueDog::Architecture::RecoveryPropulsion {
        attribute diskDiameter : LengthValue;
        attribute density : MassDensityValue;
        attribute axialInflow : SpeedValue;
        attribute requiredThrust : ForceValue;
        attribute overallEfficiency : Real;
        attribute essentialPower : PowerValue;
        attribute availableReserve : EnergyValue;
        attribute poweredDuration : TimeValue;
        attribute essentialDuration : TimeValue;
        attribute uncertaintyFactor : Real;
        attribute weedEvidenceAccepted : Boolean;
        attribute capsizeEvidenceAccepted : Boolean;
        attribute isolationEvidenceAccepted : Boolean;
        attribute thrustEvidenceAccepted : Boolean;
    }

    analysis def RecoverySizing {
        subject candidate : Candidate;
        objective sizingObjective {
            doc /* Assess whether the estimated R-002 recovery reserve fits the supplied battery reserve. This energy-only objective does not establish physical qualification or select an architecture. */
            require constraint { energyFits }
        }
        attribute thrustN : Real = candidate.requiredThrust / (1 [N]);
        attribute diameterM : Real = candidate.diskDiameter / (1 [m]);
        attribute rho : Real = candidate.density / (1 [kg/m^3]);
        attribute speed : Real = candidate.axialInflow / (1 [m/s]);
        assert constraint validInputs {
            candidate.diskDiameter > 0 [m] and candidate.density > 0 [kg/m^3] and
            candidate.axialInflow >= 0 [m/s] and candidate.requiredThrust >= 0 [N] and
            candidate.overallEfficiency > 0 and candidate.overallEfficiency <= 1 and
            candidate.essentialPower > 0 [W] and candidate.availableReserve >= 0 [J] and
            candidate.poweredDuration > 0 [s] and candidate.essentialDuration >= candidate.poweredDuration and candidate.uncertaintyFactor >= 1
        }
        out attribute idealPower : PowerValue = MarinePropulsion::IdealAxialDiskPower(thrustN, diameterM, rho, speed) * 1 [W];
        out attribute electricalPower : PowerValue = idealPower / candidate.overallEfficiency;
        return requiredReserve : EnergyValue = BlueDogRequirements::RecoveryReserveDemand(electricalPower, candidate.essentialPower, candidate.poweredDuration, candidate.essentialDuration, candidate.uncertaintyFactor);
        out attribute reserveMargin : EnergyValue = candidate.availableReserve - requiredReserve;
        out attribute energyFits : Boolean = reserveMargin >= 0 [J];
        out attribute qualificationEvidenceComplete : Boolean = candidate.weedEvidenceAccepted and candidate.capsizeEvidenceAccepted and candidate.isolationEvidenceAccepted and candidate.thrustEvidenceAccepted;
        out attribute modeledGatesMet : Boolean = energyFits and qualificationEvidenceComplete;
    }

    part waterExample : Candidate {
        doc /* Synthetic upstream example: 0.5 m/s ground speed against 1.5 m/s current. 5 N thrust is an assumed combined resistance, not a tow-test result. */
        attribute :>> diskDiameter default = 0.25 [m];
        attribute :>> density default = 1000 [kg/m^3];
        attribute :>> axialInflow default = 2 [m/s];
        attribute :>> requiredThrust default = 5 [N];
        attribute :>> overallEfficiency default = 0.5;
        attribute :>> essentialPower default = 10 [W];
        attribute :>> availableReserve default = 360000 [J];
        comment syntheticExposure /* Example route durations only; not a challenge allocation. */
        attribute :>> poweredDuration default = 1800 [s];
        attribute :>> essentialDuration default = 7200 [s];
        attribute :>> uncertaintyFactor default = 1.2;
        attribute :>> weedEvidenceAccepted default = false;
        attribute :>> capsizeEvidenceAccepted default = false;
        attribute :>> isolationEvidenceAccepted default = false;
        attribute :>> thrustEvidenceAccepted default = false;
    }
    part airExample : Candidate {
        doc /* Same assumed thrust and ground speed, with 5 m/s headwind: axial air inflow 5.5 m/s. Candidate drag and efficiency need independent measurements. */
        attribute :>> diskDiameter default = 0.25 [m];
        attribute :>> density default = 1.225 [kg/m^3];
        attribute :>> axialInflow default = 5.5 [m/s];
        attribute :>> requiredThrust default = 5 [N];
        attribute :>> overallEfficiency default = 0.5;
        attribute :>> essentialPower default = 10 [W];
        attribute :>> availableReserve default = 360000 [J];
        comment syntheticExposure /* Example route durations only; not a challenge allocation. */
        attribute :>> poweredDuration default = 1800 [s];
        attribute :>> essentialDuration default = 7200 [s];
        attribute :>> uncertaintyFactor default = 1.2;
        attribute :>> weedEvidenceAccepted default = false;
        attribute :>> capsizeEvidenceAccepted default = false;
        attribute :>> isolationEvidenceAccepted default = false;
        attribute :>> thrustEvidenceAccepted default = false;
    }
    dependency reserveCriterion from RecoverySizing to BlueDogRequirements::recoveryEnergy;
    dependency recoveryScenario from RecoverySizing to BlueDogRequirements::recoveryPropulsion;
    dependency weedGate from RecoverySizing to BlueDogRequirements::recoveryPropulsorWeeds;
    dependency capsizeGate from RecoverySizing to BlueDogRequirements::selfRighting;
    dependency controlRecoveryGate from RecoverySizing to BlueDogRequirements::capsizeControlRecovery;
    dependency isolationGate from RecoverySizing to BlueDogRequirements::motorIsolationDeadline;
    dependency isolationLatchGate from RecoverySizing to BlueDogRequirements::isolationRestartInhibition;
}

package BlueDogRecoveryRisk {
    private import ScalarValues::*;
    doc /* Sensitivity study for recovery after loss of traffic sensing. All rates
     * are hypotheses. This is not evidence that failures or collisions are rare. */
    calc def ExposureBound {
        in lossRatePerHour : Real;
        in missionHours : Real;
        in conflictRatePerHour : Real;
        in recoveryHours : Real;
        return probability : Real = (1-MarineReliability::ConstantHazardSurvival(lossRatePerHour,missionHours))*(1-MarineReliability::ConstantHazardSurvival(conflictRatePerHour,recoveryHours));
    }
    analysis Sensitivity {
        out attribute lossRatesPerHour : Real [9] ordered nonunique = (0.0001,0.0001,0.0001,0.001,0.001,0.001,0.01,0.01,0.01);
        out attribute recoveryHours : Real [9] ordered nonunique = (0.25,1,4,0.25,1,4,0.25,1,4);
        out attribute bounds : Real [9] ordered nonunique = (1..9)->ControlFunctions::collect {
            in i : Integer; ExposureBound(lossRatesPerHour#(i),48,0.1,recoveryHours#(i)) };
    }
    part disposition {
        attribute architecture : String = "Retain autonomous conspicuous shore recovery with no assumed backup detector. Minimize exposure using the reachable least-risk shore route; operator contact is not a prerequisite.";
        attribute interpretation : String = "A 48 h example passage, loss rates 1e-4 to 1e-2 per hour and 0.1 conflicting encounter per hour span sensitivity only. Every conflicting encounter is pessimistically treated as contact. The product assumes conditional independence of sensing loss and subsequent traffic; fog, waves and common-power failures can invalidate it. Analyze these as separate deterministic cases. DFMEA ranks do not supply rates.";
        attribute releaseCondition : String = "Before unattended trials, demonstrate casualty maneuvering and retention; measure installed fault exposure and local traffic; assess injury, entanglement and impediment as well as collision probability. If residual risk cannot be accepted, restrict the operating window/route or add independent protection. SRR approval does not accept that risk.";
    }
    dependency safetyBasis from disposition to GorgeChallenge::autonomousShoreRecovery;
    dependency casualtyBasis from Sensitivity to GorgeChallenge::capsizeRecovery;
}

package BlueDogRecoverySiteReview {
    private import ScalarValues::*;
    doc /* Desktop shortlist for shore-recovery assessment. Public land access does
     * not establish a navigable approach, suitable casualty landing or permission
     * for unattended operations. No coordinates are admitted to the route planner. */
    part def Candidate {
        attribute site : String;
        attribute source : String;
        attribute evidence : String;
        attribute outstanding : String;
        attribute desktopDisposition : String default = "Conditional field-survey candidate; not operationally released";
        attribute acceptedForRouting : Boolean = false;
    }
    part bingen : Candidate {
        attribute :>> site = "Bingen boat ramp and harbor";
        attribute :>> source = "https://www.portofklickitat.com/boat-launch-parks";
        attribute :>> evidence = "Port-operated ramp and harbor connect to the Columbia; same facility as the unscored launch/retrieval base.";
        attribute :>> outstanding = "Survey entrance and final capture; assess weeds, depth and current. Port rules prohibit overnight parking, so overnight retrieval logistics need a separate plan.";
    }
    part stevenson : Candidate {
        attribute :>> site = "Stevenson Cascade Avenue boat launch";
        attribute :>> source = "https://www.portofskamania.org/boat-launch-and-docks";
        attribute :>> evidence = "Port identifies a public launch at the east end of Cascade Avenue, near the western end of the course.";
        attribute :>> outstanding = "Assess approach, exposure, ramps versus rock shoreline, competing launch traffic and casualty capture.";
    }
    part springCreek : Candidate {
        attribute :>> site = "Spring Creek Hatchery State Park";
        attribute :>> source = "https://parks.wa.gov/find-parks/state-parks/spring-creek-hatchery-state-park";
        attribute :>> evidence = "State park on the Columbia provides a candidate north-bank access location for field assessment.";
        attribute :>> outstanding = "Confirm access hours, appropriate retrieval frontage, rocks, current, park conditions and wind-sport conflicts; not a sheltered-harbor assumption.";
    }
    part viento : Candidate {
        attribute :>> site = "Viento State Park";
        attribute :>> source = "https://stateparks.oregon.gov/index.cfm?do=park.profile&parkId=123";
        attribute :>> evidence = "Official park map identifies river access, making it a candidate south-bank retrieval location.";
        attribute :>> outstanding = "Assess accessible carry path, rocky landing and exposure. Cross-river traffic and current may make it inferior to a farther same-bank location.";
    }
    part homeValley : Candidate {
        attribute :>> site = "Home Valley shoreline / Wind River launch sector";
        attribute :>> source = "https://www.skamaniacounty.gov/departments-offices/public-works/parks-and-campgrounds";
        attribute :>> evidence = "County-managed Home Valley park provides an intermediate north-bank access sector. County code 12.04.290 separately identifies Wind River launch and permit requirements.";
        attribute :>> outstanding = "Survey river frontage and separate swim/recreation areas from recovery approaches; establish day/night pickup access and water-level limits. Do not equate beach access with a safe motor approach.";
    }
    part drano : Candidate {
        attribute :>> site = "Drano Lake";
        attribute :>> source = "https://wdfw.wa.gov/places-to-go/life-outdoors/southwest";
        attribute :>> evidence = "WDFW identifies heavy fishing use and launch congestion. The lake entrance also adds road/rail bridge passage to casualty recovery.";
        attribute :>> outstanding = "Excluded from the initial autonomous destination set. Reconsider only with entrance clearance, traffic and capture evidence.";
        attribute :>> desktopDisposition = "Reject as default autonomous recovery destination";
    }
    part selection {
        attribute primarySites : String = "Bingen harbor at the east end; Stevenson launch at the west end. Carry equipment for ramp or bank capture: Stevenson seasonal docks are not assumed in winter.";
        attribute intermediateSites : String = "Prioritize a north-bank Home Valley retrieval survey; retain Spring Creek and south-bank Viento as alternatives. Do not route a casualty across the commercial corridor merely because a south-bank site is closer.";
        attribute coverageDecision : String = "Endpoint-only recovery is not an accepted architecture: between endpoints it can require tens of kilometres of transit, and adverse-current authority is not demonstrated. Recovery feasibility requires a route/casualty coverage map for each forecast scenario using surveyed approaches. Any uncovered position or loss of recovery authority prevents launch or requires an earlier abort. No arbitrary point on the shoreline counts as retrieval.";
        attribute fieldProtocol : String = "At each site record WGS84 approach polygon, chart and actual depth at stated pool level, submerged/overhead obstacles, weeds/nets, drift and landing exposure, casualty retention method, legal walking/vehicle access, access hours, and one-person pickup time. Photograph and run a supervised drifting/capsized capture. Owner conducts access/physical observations; analysis agent integrates measured records and repeats route reserve checks.";
    }
    metadata rationale : ModelingMetadata::Rationale { text = "Assess more than the two endpoints so recovery distance can vary with position and remaining authority. These source-backed candidates narrow the field survey; none is yet a safe harbor or an approved numerical destination. Source review date: 2026-10-12."; }
    dependency reserveAssessment from bingen to GorgeChallenge::courseRecoveryReserve;
    dependency westernRecovery from stevenson to GorgeChallenge::autonomousShoreRecovery;
    dependency intermediateRecovery from springCreek to GorgeChallenge::autonomousShoreRecovery;
    dependency oppositeBankRecovery from viento to GorgeChallenge::autonomousShoreRecovery;
}

package BlueDogHydrostatics {
    private import ScalarValues::*;
    public import MarineHydrostatics::*;
    analysis analyticExample {
        out attribute partial : Real [4] ordered nonunique = WetMoment((0.0,0.0,0.0,1.0,0.0,0.0,0.0,1.0,0.0,0.0,0.0,1.0),0.5);
        out attribute full : Real [4] ordered nonunique = WetMoment((0.0,0.0,0.0,1.0,0.0,0.0,0.0,1.0,0.0,0.0,0.0,1.0),1.0);
    }
    dependency recoveryGeometry from MeshMoments to BlueDogRequirements::selfRighting;
}

package BlueDogReliability {
    private import ScalarValues::*;
    private import ISQ::*;
    private import SI::*;
    doc /* Conditional constant-hazard exposure model, not a sailing simulator.
     * Water VMG already includes heading/tacking; current is signed along route.
     * Rates must be mission-critical, non-overlapping and confidence-qualified.
     * No repair, independence of random modes and constant hazard are assumptions.
     * Common-cause exposure is explicit. DFMEA rankings are not failure rates.
     * Each profile is conditional on its declared weather trajectory. Integrate
     * route success and survival over trajectories, not hazard at mean successful
     * duration. BlueDogWeather::policy separates challenge and winter exposure.
     */
    part def SailingLeg {
        attribute distance : LengthValue;
        attribute waterVMG : SpeedValue;
        attribute currentVMG : SpeedValue;
        attribute retainedPerformance : Real;
        attribute groundVMG : SpeedValue = waterVMG * retainedPerformance + currentVMG;
        attribute valid : Boolean = distance > 0 [m] and waterVMG > 0 [m/s] and
        retainedPerformance > 0 and retainedPerformance <= 1 and groundVMG > 0 [m/s];
        attribute travelTime : TimeValue = if valid ? distance / groundVMG else 0 [s];
    }
    part def VoyageProfile {
        ref part vessel : BlueDog::Architecture::Boat;
        part legs : SailingLeg [1..*] ordered;
        attribute holdTime : TimeValue;
        attribute qualifiedDuration : TimeValue;
        attribute criticalRatesPerHour : Real [1..*] ordered nonunique;
        attribute commonCauseRatePerHour : Real;
        attribute zeroFailureTestHours : Real;
        attribute observedCriticalFailures : Integer;
        attribute profileEvidenceAccepted : Boolean;
        attribute rateEvidenceAccepted : Boolean;
        attribute constantHazardAccepted : Boolean;
        attribute criticalFunctionPartitionAccepted : Boolean default = false;
        attribute dependenceTreatmentAccepted : Boolean default = false;
        attribute commonCauseCoverageAccepted : Boolean default = false;
        comment rateBasis /* Review assertions, not measured rates or proof of independence.
         * Establish non-overlapping critical-function loss terms, dependence treatment
         * and common-cause coverage for this configuration/profile before crediting
         * the study evidence. A primary component fault need not be function loss.
         * NIST Handbook 8.1.8 and defense R&M BoK 2025 section 3.2.4 inform this basis. */
        attribute totalRatePerHour : Real = NumericalFunctions::sum(criticalRatesPerHour) + commonCauseRatePerHour;
        attribute voyageDuration : TimeValue = NumericalFunctions::sum(legs.travelTime) + holdTime;
        attribute valid : Boolean = SequenceFunctions::size(legs) > 0 and
        legs->ControlFunctions::forAll { in leg : SailingLeg; leg.valid } and
        holdTime >= 0 [s] and qualifiedDuration > 0 [s] and
        SequenceFunctions::size(criticalRatesPerHour) > 0 and
        criticalRatesPerHour->ControlFunctions::forAll { in rate : Real; rate >= 0 } and
        commonCauseRatePerHour >= 0 and zeroFailureTestHours > 0 and observedCriticalFailures >= 0;
    }
    analysis def CruiseReliability {
        subject profile : VoyageProfile;
        out attribute inputsValid : Boolean = profile.valid;
        assert constraint validInputs { inputsValid }
        out attribute groundSpeeds : SpeedValue [*] ordered nonunique = profile.legs.groundVMG;
        out attribute voyageHours : Real = profile.voyageDuration / (3600 [s]);
        out attribute minimumProgressMet : Boolean = BlueDogRequirements::LegProgressCriterion(groundSpeeds);
        out attribute durationMet : Boolean = BlueDogRequirements::PassageDurationCriterion(profile.voyageDuration, profile.qualifiedDuration);
        out attribute allowableRatePerHour : Real = if inputsValid ? MarineReliability::EqualSurvivalRate(0.90, voyageHours) else 0;
        out attribute modeledReliability : Real = if inputsValid ? MarineReliability::ConstantHazardSurvival(profile.totalRatePerHour, voyageHours) else 0;
        out attribute rateBudgetMet : Boolean = inputsValid and BlueDogRequirements::FailureRateCriterion(profile.totalRatePerHour, voyageHours);
        out attribute requiredZeroFailureHours : Real = if inputsValid ? -OpenSysMLMathFunctions::ln(0.05) / allowableRatePerHour else 0;
        out attribute demonstrationApplicable : Boolean = inputsValid and profile.observedCriticalFailures == 0;
        out attribute zeroFailureUpperRate : Real = if demonstrationApplicable ? -OpenSysMLMathFunctions::ln(0.05) / profile.zeroFailureTestHours else 0;
        out attribute demonstratedReliabilityLowerBound : Real = if demonstrationApplicable ? OpenSysMLMathFunctions::exp(-zeroFailureUpperRate * voyageHours) else 0;
        out attribute demonstrationMet : Boolean = demonstrationApplicable and BlueDogRequirements::MissionReliabilityCriterion(demonstratedReliabilityLowerBound, 0.95);
        out attribute evidenceReady : Boolean = profile.profileEvidenceAccepted and profile.rateEvidenceAccepted and profile.constantHazardAccepted
        and profile.criticalFunctionPartitionAccepted and profile.dependenceTreatmentAccepted and profile.commonCauseCoverageAccepted;
        comment provisionalScreens /* minimumProgressMet is a legacy comparison and rateBudgetMet evaluates a provisional objective; neither constrains mission feasibility. */
        return modeledFeasible : Boolean = inputsValid and durationMet;
        out attribute reliabilitySupported : Boolean = modeledFeasible and rateBudgetMet and demonstrationMet and evidenceReady;
        objective feasibility { require constraint { modeledFeasible } }
    }
    verification def VoyageReliabilityVerification {
        metadata plannedAnalyze : VerificationCases::VerificationMethod { kind = VerificationCases::VerificationMethodKind::analyze; }
        doc /*
         *  Study assessment of provisional L-101 and L-102 only. A failed numerical study target does not fail a binding product or evidence-process requirement. L-103, Q-101 and Q-103 retain their independent planned review objectives. */
        subject profile : VoyageProfile;
        analysis calculation : CruiseReliability { subject = profile; }
        objective reliabilityAcceptance {
            verify BlueDogRequirements::missionSuccessProbability;
            verify BlueDogRequirements::failureRateBudget;
            require constraint { calculation.reliabilitySupported }
        }
        return verdict : VerificationCases::VerdictKind =
            if not calculation.evidenceReady ? VerificationCases::VerdictKind::inconclusive
        else VerificationCases::PassIf(calculation.reliabilitySupported);
    }
    dependency progressCriterion from CruiseReliability to BlueDogRequirements::legProgress;
    dependency durationCriterion from CruiseReliability to BlueDogRequirements::passageDuration;
    dependency reliabilityCriterion from CruiseReliability to BlueDogRequirements::missionSuccessProbability;
    dependency budgetCriterion from CruiseReliability to BlueDogRequirements::failureRateBudget;
    dependency evidenceCriterion from CruiseReliability to BlueDogRequirements::reliabilityEvidence;
    dependency cruiseEvidenceCriterion from CruiseReliability to BlueDogRequirements::cruiseEvidence;
    dependency durationEnergyCoupling from CruiseReliability to BlueDogEnergy::SustainedOperation;
    dependency currentContext from CruiseReliability to BlueDogRequirements::gorgeCurrent;
    dependency weedContext from CruiseReliability to BlueDogRequirements::submergedWeedPassage;
    verification def PassageDurationVerification {
        metadata plannedAnalyze : VerificationCases::VerificationMethod { kind = VerificationCases::VerificationMethodKind::analyze; }
        doc /* Evaluate Q-102 independently of the provisional reliability target and demonstration duration. This checks the supplied profile only; whole-route ensemble completeness and installed qualification evidence remain separate review objectives. */
        subject profile : VoyageProfile;
        attribute profileValid : Boolean = SequenceFunctions::size(profile.legs) > 0 and
        profile.legs->ControlFunctions::forAll { in leg : SailingLeg; leg.valid } and
        profile.holdTime >= 0 [s] and profile.qualifiedDuration > 0 [s];
        attribute durationMet : Boolean = BlueDogRequirements::PassageDurationCriterion(profile.voyageDuration, profile.qualifiedDuration);
        objective durationAcceptance {
            verify BlueDogRequirements::passageDuration;
            require constraint { profileValid and durationMet }
        }
        return verdict : VerificationCases::VerdictKind =
            if not profile.profileEvidenceAccepted ? VerificationCases::VerdictKind::inconclusive
        else VerificationCases::PassIf(profileValid and durationMet);
    }

}

package BlueDogSafety {
    private import ScalarValues::*;
    doc /* Initial current-Gorge hazard/control argument, not complete coverage or
     * accepted risk. MIL-STD-882E Change1 sections 4.3 and Task106, NASA SE
     * Handbook6.4 and defense R&M BoK2025 inform the structure. Project scales
     * and acceptance responsibilities remain to be established; no DoD matrix
     * or authority is adopted. Proposed controls have no credited effectiveness. */
    part def HazardRecord {
        attribute identifier : String [1];
        ref part configuration : MarineDesign::Design [1] = BlueDogIC01::design;
        attribute condition : String [1];
        attribute potentialMishap : String [1];
        attribute modes : String [1];
        attribute ownerRole : String [1];
        attribute controlIntent : String [1];
        attribute implementationEvidenceAccepted : Boolean default = false;
        attribute effectivenessEvidenceAccepted : Boolean default = false;
        attribute residualRiskAssessmentAccepted : Boolean default = false;
        attribute riskDispositionAccepted : Boolean default = false;
        attribute controlEvidenceRecord : String [0..1];
        attribute acceptanceRecord : String [0..1];
        attribute acceptanceAuthority : String [0..1];
        attribute recordsIdentified : Boolean = SequenceFunctions::size(controlEvidenceRecord) == 1 and
        SequenceFunctions::size(acceptanceRecord) == 1 and SequenceFunctions::size(acceptanceAuthority) == 1 and
        controlEvidenceRecord->ControlFunctions::forAll { in value : String; value != "" } and
        acceptanceRecord->ControlFunctions::forAll { in value : String; value != "" } and
        acceptanceAuthority->ControlFunctions::forAll { in value : String; value != "" };
        attribute contextIdentified : Boolean = identifier != "" and condition != "" and potentialMishap != "" and
        modes != "" and ownerRole != "" and controlIntent != "";
        attribute closed : Boolean = contextIdentified and implementationEvidenceAccepted and effectivenessEvidenceAccepted and
        residualRiskAssessmentAccepted and riskDispositionAccepted and recordsIdentified;
        metadata workStatus : ModelingMetadata::StatusInfo { status = ModelingMetadata::StatusKind::open; }
        metadata risk : RiskMetadata::Risk;
        doc /* Closed is a modeled review precondition over supplied dispositions
         * and record identities. It does not inspect records or accept risk.
         * Existing RiskMetadata levels are unassessed, not a numerical hazard
         * matrix or a zero/low risk assertion. Contributor links describe credible
         * mechanisms, not probabilities or inevitable mishaps. */
    }
    part def HazardSet {
        ref part failureReview : FailureAnalysis::Review [1];
        part hazards : HazardRecord [1..*];
        attribute scopeReviewed : Boolean default = false;
    }
    part gorge : HazardSet {
        ref part :>> failureReview = BlueDogDFMEA::starter;
        part collisionExposure : HazardRecord subsets hazards {
            attribute :>> identifier = "HAZ-01";
            attribute :>> condition = "Unsafe motion or clearance in the presence of people, craft or their equipment";
            attribute :>> potentialMishap = "Collision, strike or entanglement affecting other waterway users";
            attribute :>> modes = "Sailing, holds, degraded operation and powered/unpowered recovery";
            attribute :>> ownerRole = "Safety/navigation";
            attribute :>> controlIntent = "Admit only supported sensing/maneuver conditions; preserve lookout/avoidance and assess the independent recovery path. Controls and secondary effects need evidence.";
        }
        part boundaryLoss : HazardRecord subsets hazards {
            attribute :>> identifier = "HAZ-02";
            attribute :>> condition = "Required navigation or control cannot retain the approved water envelope";
            attribute :>> potentialMishap = "Grounding or hazardous interaction with excluded waterway structures and traffic";
            attribute :>> modes = "Sailing, waiting, degraded navigation and recovery";
            attribute :>> ownerRole = "Navigation/recovery";
            attribute :>> controlIntent = "Validate the permitted domain and uncertainty; retain current observations, boundary supervision and a supported recovery response. A planner result alone is insufficient.";
        }
        part unintendedThrust : HazardRecord subsets hazards {
            attribute :>> identifier = "HAZ-03";
            attribute :>> condition = "Motor thrust is enabled without current safe authority or during human handling";
            attribute :>> potentialMishap = "Propeller/contact or entanglement exposure; unwanted propulsion also ends qualification";
            attribute :>> modes = "Launch, qualifying attempt, restart, recovery, capture and service";
            attribute :>> ownerRole = "Recovery/handling";
            attribute :>> controlIntent = "Establish current authority, known nonqualifying state, durable disqualification and effective isolation. Driver faults and handling exposure require physical controls and trials.";
        }
        part flotationRetentionLoss : HazardRecord subsets hazards {
            attribute :>> identifier = "HAZ-04";
            attribute :>> condition = "Casualty load or ingress defeats flotation or major-component retention";
            attribute :>> potentialMishap = "Vessel loss or released components/debris affecting people, property or the environment";
            attribute :>> modes = "Loaded operation, capsize, flooding, recovery and retrieval";
            attribute :>> ownerRole = "Hull/structure";
            attribute :>> controlIntent = "Establish configuration-specific flotation, load paths and retention under casualty exposure; assess hazards introduced by retention choices. Static intact volume alone is insufficient.";
        }
        part electricalThermalExposure : HazardRecord subsets hazards {
            attribute :>> identifier = "HAZ-05";
            attribute :>> condition = "Water, faults, charging or temperature compromise energy containment and required electrical function";
            attribute :>> potentialMishap = "Thermal/electrical/material exposure to people or vessel and loss of required functions";
            attribute :>> modes = "Charging, bench testing, operation, casualty recovery and service";
            attribute :>> ownerRole = "Power/system safety";
            attribute :>> controlIntent = "Evaluate design/containment/protection alternatives, ingress and thermal limits, supply transients and safe service isolation using the selected installation. No component or protection scheme is selected by this record.";
        }
        part handlingRetrievalExposure : HazardRecord subsets hazards {
            attribute :>> identifier = "HAZ-06";
            attribute :>> condition = "Approach, capture, retention or lifting cannot be completed with the admitted site and handling arrangement";
            attribute :>> potentialMishap = "Operator fall/contact/exposure or vessel escape during attempted retrieval";
            attribute :>> modes = "Transport, launch, shore capture, pickup and maintenance handling";
            attribute :>> ownerRole = "Owner/handling";
            attribute :>> controlIntent = "Review site access and handling design before relying on procedures; validate the full one-person task and retained vessel rather than approach alone. Preserve failed/incomplete trials.";
        }
    }
    analysis def SafetyReview {
        subject assessment : HazardSet;
        analysis failureModes : FailureAnalysis::DesignFailureReview { subject = assessment.failureReview; }
        out attribute hazardCount : Integer = SequenceFunctions::size(assessment.hazards);
        out attribute unresolvedHazardCount : Integer = NumericalFunctions::sum(
            assessment.hazards->ControlFunctions::collect { in hazard : HazardRecord; if hazard.closed ? 0 else 1 });
        out attribute hazardRecordsClosed : Boolean = hazardCount > 0 and
        assessment.hazards->ControlFunctions::forAll { in hazard : HazardRecord; hazard.closed };
        out attribute fmeaReady : Boolean = failureModes.reviewReady;
        out attribute reviewReady : Boolean = assessment.scopeReviewed and fmeaReady and hazardRecordsClosed;
        return ready : Boolean = reviewReady;
        doc /* Uses the native FMEA review and explicit hazard dispositions.
         * A successful calculation is not safety qualification or risk acceptance. */
    }
    analysis currentReview : SafetyReview { subject = gorge; }
    dependency dispositionBasis from SafetyReview to BlueDogRequirements::criticalFailureDisposition;
    metadata issue : ModelingMetadata::Issue {
        text = "S-01: Complete lifecycle/mode/human/environment hazard coverage, including manufacturing materials, storage, charging and disposal; the initial six hazards are not exhaustive. S-02: Establish likelihood/consequence/uncertainty and project risk criteria without treating unknown as low. S-03: Select and verify controls, secondary effects and common-cause isolation on the installed configuration. S-04: Record actual effectiveness evidence and residual-risk dispositions with the responsible authority; all current hazard and failure actions remain open. S-05: Justify non-overlapping critical-function rate terms, dependence/common-cause treatment and exposure/statistical applicability before crediting reliability evidence.";
    }
    dependency collisionExposureControl1 from gorge::collisionExposure to BlueDogRequirements::trafficSafety;
    dependency collisionExposureControl2 from gorge::collisionExposure to BlueDogRequirements::navigationAvailability;
    dependency collisionExposureVerification1 from gorge::collisionExposure to BlueDogRequirementVerification::TrafficSafetyVerification;
    dependency collisionExposureVerification2 from gorge::collisionExposure to GorgeChallengeVerification::WindSportEncounterVerification;
    dependency boundaryLossControl1 from gorge::boundaryLoss to BlueDogRequirements::operatingBoundary;
    dependency boundaryLossControl2 from gorge::boundaryLoss to GorgeChallenge::restrictedWaters;
    dependency boundaryLossVerification1 from gorge::boundaryLoss to BlueDogRequirementVerification::OperatingBoundaryVerification;
    dependency boundaryLossVerification2 from gorge::boundaryLoss to GorgeChallengeVerification::RestrictedWatersVerification;
    dependency unintendedThrustControl1 from gorge::unintendedThrust to BlueDogRequirements::challengeMotorInhibition;
    dependency unintendedThrustControl2 from gorge::unintendedThrust to BlueDogRequirements::motorIsolationDeadline;
    dependency unintendedThrustControl3 from gorge::unintendedThrust to BlueDogRequirements::qualificationPersistence;
    dependency unintendedThrustVerification1 from gorge::unintendedThrust to BlueDogVerificationPlanning::InterfaceAndDurabilityIntegrationVerification;
    dependency unintendedThrustVerification2 from gorge::unintendedThrust to BlueDogRequirementVerification::EmergencyControlVerification;
    dependency flotationRetentionLossControl1 from gorge::flotationRetentionLoss to GorgeChallenge::casualtyFlotation;
    dependency flotationRetentionLossControl2 from gorge::flotationRetentionLoss to GorgeChallenge::majorComponentRetention;
    dependency flotationRetentionLossControl3 from gorge::flotationRetentionLoss to BlueDogStructure::structuralIntegrity;
    dependency flotationRetentionLossVerification1 from gorge::flotationRetentionLoss to BlueDogRequirementVerification::FlotationEvidence;
    dependency flotationRetentionLossVerification2 from gorge::flotationRetentionLoss to GorgeChallengeVerification::MajorComponentRetentionVerification;
    dependency electricalThermalExposureControl1 from gorge::electricalThermalExposure to BlueDogRequirements::wetElectricalIntegrity;
    dependency electricalThermalExposureControl2 from gorge::electricalThermalExposure to BlueDogRequirements::peakSupplyCapability;
    dependency electricalThermalExposureControl3 from gorge::electricalThermalExposure to BlueDogRequirements::batteryChargeTemperatureInhibition;
    dependency electricalThermalExposureVerification1 from gorge::electricalThermalExposure to BlueDogRequirementVerification::WetElectricalIntegrityVerification;
    dependency electricalThermalExposureVerification2 from gorge::electricalThermalExposure to BlueDogRequirementVerification::PeakSupplyCapabilityVerification;
    dependency electricalThermalExposureVerification3 from gorge::electricalThermalExposure to BlueDogRequirementVerification::SolarHeatingVerification;
    dependency handlingRetrievalExposureControl1 from gorge::handlingRetrievalExposure to BlueDogRequirements::soloRetrieval;
    dependency handlingRetrievalExposureControl2 from gorge::handlingRetrievalExposure to BlueDogRequirements::transportability;
    dependency handlingRetrievalExposureControl3 from gorge::handlingRetrievalExposure to BlueDogStructure::launchClearance;
    dependency handlingRetrievalExposureVerification1 from gorge::handlingRetrievalExposure to BlueDogVerificationPlanning::HumanRecoveryUseValidation;
    dependency handlingRetrievalExposureVerification2 from gorge::handlingRetrievalExposure to BlueDogRequirementVerification::LaunchSiteEvidence;
    dependency handlingRetrievalExposureVerification3 from gorge::handlingRetrievalExposure to BlueDogRequirementVerification::TransportabilityVerification;

    dependency collisionExposureContributor1 from gorge::collisionExposure to BlueDogDFMEA::starter::steeringJam {
        metadata rationale : ModelingMetadata::Rationale { text = "Possible contributing mechanism in this hazard's stated modes; supporting basis, not an inevitable mishap or numerical probability."; }
    }
    dependency collisionExposureContributor2 from gorge::collisionExposure to BlueDogDFMEA::starter::sailJam {
        metadata rationale : ModelingMetadata::Rationale { text = "Possible contributing mechanism in this hazard's stated modes; supporting basis, not an inevitable mishap or numerical probability."; }
    }
    dependency collisionExposureContributor3 from gorge::collisionExposure to BlueDogDFMEA::starter::powerCommonCause {
        metadata rationale : ModelingMetadata::Rationale { text = "Possible contributing mechanism in this hazard's stated modes; supporting basis, not an inevitable mishap or numerical probability."; }
    }
    dependency collisionExposureContributor4 from gorge::collisionExposure to BlueDogDFMEA::starter::navigationFault {
        metadata rationale : ModelingMetadata::Rationale { text = "Possible contributing mechanism in this hazard's stated modes; supporting basis, not an inevitable mishap or numerical probability."; }
    }
    dependency collisionExposureContributor5 from gorge::collisionExposure to BlueDogDFMEA::starter::controlLockup {
        metadata rationale : ModelingMetadata::Rationale { text = "Possible contributing mechanism in this hazard's stated modes; supporting basis, not an inevitable mishap or numerical probability."; }
    }
    dependency collisionExposureContributor6 from gorge::collisionExposure to BlueDogDFMEA::starter::trafficMiss {
        metadata rationale : ModelingMetadata::Rationale { text = "Possible contributing mechanism in this hazard's stated modes; supporting basis, not an inevitable mishap or numerical probability."; }
    }
    dependency collisionExposureContributor7 from gorge::collisionExposure to BlueDogDFMEA::starter::commandContextFault {
        metadata rationale : ModelingMetadata::Rationale { text = "Possible contributing mechanism in this hazard's stated modes; supporting basis, not an inevitable mishap or numerical probability."; }
    }
    dependency collisionExposureContributor8 from gorge::collisionExposure to BlueDogDFMEA::starter::commonSensingFault {
        metadata rationale : ModelingMetadata::Rationale { text = "Possible contributing mechanism in this hazard's stated modes; supporting basis, not an inevitable mishap or numerical probability."; }
    }
    dependency boundaryLossContributor1 from gorge::boundaryLoss to BlueDogDFMEA::starter::steeringJam {
        metadata rationale : ModelingMetadata::Rationale { text = "Possible contributing mechanism in this hazard's stated modes; supporting basis, not an inevitable mishap or numerical probability."; }
    }
    dependency boundaryLossContributor2 from gorge::boundaryLoss to BlueDogDFMEA::starter::powerCommonCause {
        metadata rationale : ModelingMetadata::Rationale { text = "Possible contributing mechanism in this hazard's stated modes; supporting basis, not an inevitable mishap or numerical probability."; }
    }
    dependency boundaryLossContributor3 from gorge::boundaryLoss to BlueDogDFMEA::starter::navigationFault {
        metadata rationale : ModelingMetadata::Rationale { text = "Possible contributing mechanism in this hazard's stated modes; supporting basis, not an inevitable mishap or numerical probability."; }
    }
    dependency boundaryLossContributor4 from gorge::boundaryLoss to BlueDogDFMEA::starter::controlLockup {
        metadata rationale : ModelingMetadata::Rationale { text = "Possible contributing mechanism in this hazard's stated modes; supporting basis, not an inevitable mishap or numerical probability."; }
    }
    dependency boundaryLossContributor5 from gorge::boundaryLoss to BlueDogDFMEA::starter::commandContextFault {
        metadata rationale : ModelingMetadata::Rationale { text = "Possible contributing mechanism in this hazard's stated modes; supporting basis, not an inevitable mishap or numerical probability."; }
    }
    dependency boundaryLossContributor6 from gorge::boundaryLoss to BlueDogDFMEA::starter::commonSensingFault {
        metadata rationale : ModelingMetadata::Rationale { text = "Possible contributing mechanism in this hazard's stated modes; supporting basis, not an inevitable mishap or numerical probability."; }
    }
    dependency unintendedThrustContributor1 from gorge::unintendedThrust to BlueDogDFMEA::starter::motorUncommanded {
        metadata rationale : ModelingMetadata::Rationale { text = "Possible contributing mechanism in this hazard's stated modes; supporting basis, not an inevitable mishap or numerical probability."; }
    }
    dependency unintendedThrustContributor2 from gorge::unintendedThrust to BlueDogDFMEA::starter::controlLockup {
        metadata rationale : ModelingMetadata::Rationale { text = "Possible contributing mechanism in this hazard's stated modes; supporting basis, not an inevitable mishap or numerical probability."; }
    }
    dependency unintendedThrustContributor3 from gorge::unintendedThrust to BlueDogDFMEA::starter::commandContextFault {
        metadata rationale : ModelingMetadata::Rationale { text = "Possible contributing mechanism in this hazard's stated modes; supporting basis, not an inevitable mishap or numerical probability."; }
    }
    dependency flotationRetentionLossContributor1 from gorge::flotationRetentionLoss to BlueDogDFMEA::starter::hullLeak {
        metadata rationale : ModelingMetadata::Rationale { text = "Possible contributing mechanism in this hazard's stated modes; supporting basis, not an inevitable mishap or numerical probability."; }
    }
    dependency flotationRetentionLossContributor2 from gorge::flotationRetentionLoss to BlueDogDFMEA::starter::keelLoss {
        metadata rationale : ModelingMetadata::Rationale { text = "Possible contributing mechanism in this hazard's stated modes; supporting basis, not an inevitable mishap or numerical probability."; }
    }
    dependency flotationRetentionLossContributor3 from gorge::flotationRetentionLoss to BlueDogDFMEA::starter::sailJam {
        metadata rationale : ModelingMetadata::Rationale { text = "Possible contributing mechanism in this hazard's stated modes; supporting basis, not an inevitable mishap or numerical probability."; }
    }
    dependency electricalThermalExposureContributor1 from gorge::electricalThermalExposure to BlueDogDFMEA::starter::batteryFault {
        metadata rationale : ModelingMetadata::Rationale { text = "Possible contributing mechanism in this hazard's stated modes; supporting basis, not an inevitable mishap or numerical probability."; }
    }
    dependency electricalThermalExposureContributor2 from gorge::electricalThermalExposure to BlueDogDFMEA::starter::hullLeak {
        metadata rationale : ModelingMetadata::Rationale { text = "Possible contributing mechanism in this hazard's stated modes; supporting basis, not an inevitable mishap or numerical probability."; }
    }
    dependency electricalThermalExposureContributor3 from gorge::electricalThermalExposure to BlueDogDFMEA::starter::powerCommonCause {
        metadata rationale : ModelingMetadata::Rationale { text = "Possible contributing mechanism in this hazard's stated modes; supporting basis, not an inevitable mishap or numerical probability."; }
    }
    dependency handlingRetrievalExposureContributor1 from gorge::handlingRetrievalExposure to BlueDogDFMEA::starter::recoveryCaptureFault {
        metadata rationale : ModelingMetadata::Rationale { text = "Possible contributing mechanism in this hazard's stated modes; supporting basis, not an inevitable mishap or numerical probability."; }
    }
    dependency handlingRetrievalExposureContributor2 from gorge::handlingRetrievalExposure to BlueDogDFMEA::starter::steeringJam {
        metadata rationale : ModelingMetadata::Rationale { text = "Possible contributing mechanism in this hazard's stated modes; supporting basis, not an inevitable mishap or numerical probability."; }
    }
}

package BlueDogSailTrade {
    doc /* Control architecture and section camber are independent design axes.
     * A cambered wing could also use aerodynamic tail control. These three named
     * configurations are a starting comparison, not mutually exclusive physics. */
    private import ScalarValues::*;
    enum def Evidence { unknown; passed; failed; }
    part def Candidate {
        attribute label : String;
        attribute membraneSail : Boolean;
        attribute aerodynamicTrim : Boolean;
        attribute concept : String;
        attribute durability : String;
        attribute energy : String;
        attribute sailing : String;
        attribute recovery : String;
        attribute manufacturing : String;
        attribute nextEvidence : String;
        // Ordered: wet/survival durability, energy, polar/progress, capsize/control,
        // manufacturing, lifting, voyage reliability. Unknown is never a failure.
        attribute gates : Evidence [7] ordered nonunique default =
            (Evidence::unknown, Evidence::unknown, Evidence::unknown, Evidence::unknown,
            Evidence::unknown, Evidence::unknown, Evidence::unknown);
    }
    part tailWing : Candidate {
        attribute :>> label = "Tail-controlled rigid wing";
        attribute :>> membraneSail = false;
        attribute :>> aerodynamicTrim = true;
        attribute :>> concept = "Freely rotating main wing, provisionally symmetric, with a tail and actuated elevator-like trim tab. Tail/wing aerodynamic moments set incidence; no assumption of a powered whole-wing bearing.";
        attribute :>> durability = "Avoids sailcloth flogging and sheets; retains bearing, tab linkage, tail-boom, skin/joint and wave-impact failure modes. Rigid wings are not automatically storm-proof.";
        attribute :>> energy = "Low trim-energy potential from aerodynamic balance; measure bearing friction, tab hinge moment and failure-state power. No transfer of full-size Saildrone wattage to Blue Dog.";
        attribute :>> sailing = "Test both tacks and low-Reynolds-number main-wing/tail interaction. Tail authority, stall, gust response and faulted-tab loads remain open.";
        attribute :>> recovery = "Include main wing, tail, boom, tab, actuator and any counterweight as separate mass/volume bodies. Check free, jammed and failed trim states plus sealed, flooded and draining states.";
        attribute :>> manufacturing = "Compatible in principle with printed ribs and glass skins; extra bearings, waterproof actuation, alignment and tail clearance need design.";
        attribute :>> nextEvidence = "Low-speed trim bench; unpowered and jammed-tab gust tests; wet-cycle endurance; actual rig mass/CG and compartment geometry.";
        metadata rationale : ModelingMetadata::Rationale { text = "Equal development contender for the finite Gorge mission; passive trim and cloth/line wear are trade criteria, not demonstrated reliability advantages. Primary-source notes and limitations are linked through BlueDogSourceEvidence."; }
    }
    part camberedWing : Candidate {
        attribute :>> label = "Fixed-camber rotating-mast wing";
        attribute :>> membraneSail = false;
        attribute :>> aerodynamicTrim = false;
        attribute :>> concept = "Owner-defined fixed-camber CrescentWing with whole-mast rotation for trim. Square-sail/downwind mode and reaching mode; no camber reversal, flap or tail mechanism is assumed. Evaluate a non-backdrivable gearbox for unpowered position holding as an actuator option, not a selected component.";
        attribute :>> durability = "Avoids cloth flogging and camber-changing joints; retains skin, seam, mast-bearing and trim-drive fatigue and wave-impact loads. Verify holding torque and wear under shock, vibration, lubrication and temperature variation; do not assume every worm gearbox self-locks.";
        attribute :>> energy = "Non-backdrivable gearing may eliminate motor holding current, but not controller standby power or trim energy. Compare measured daily move, hold and idle energy against tail control; include starting friction, gearbox efficiency, trim frequency and gust response. A balanced pivot can reduce drive torque.";
        attribute :>> sailing = "Measure full-angle lift, drag and moment on both tacks, including drag-dominated square/downwind and lift-dominated reaching modes and transitions. Do not inherit symmetric linear-wing polars. Inspect edge geometry before assuming leading/trailing-edge interchange.";
        attribute :>> recovery = "Use actual crescent/swept geometry, dry and retained-water CG, sealed volume, trim angle and failed-drive position. A self-locking drive retains the last trim angle on power loss and cannot passively feather without a release mechanism. Assess locked-angle storm/capsize states and any clutch or emergency depower strategy. Manufacturing CAD is not qualified challenge-vessel geometry.";
        attribute :>> manufacturing = "Closest to existing CAD and useful for coupons/prototypes. Fixed section and rotating mast avoid tail/tab/boom parts; bearing, drive and waterproofing details remain to be designed.";
        attribute :>> nextEvidence = "Inspect CAD section and stations; measure both-mode, both-tack polars, trim moments and drive energy, including depower and jam states; compare against MaxiMOOP and Oshen PC13 directly driven wingsail precedent. Bench-test motor-off holding, wet-cycle wear, daily energy and failed-power depower/recovery; include gearbox mass and CG.";
        metadata rationale : ModelingMetadata::Rationale { text = "Owner confirmed fixed camber, whole-mast trim and square/downwind plus reaching modes. Miller et al., An Alternative Wing Sail Concept for Small Autonomous Sailing Craft, DOI 10.1007/978-3-319-72739-4_1, provides analogous square-sail-derived precedent, not Blue Dog qualification. Oshen PC13 provides ocean-service precedent for directly actuated DynaRig wingsails (https://www.microtransat.org/content.php?p=2026_oshen_cstar), not evidence of identical camber or a non-backdrivable gearbox. Retain alongside tail control pending comparable measurements."; }
    }
    part softSail : Candidate {
        attribute :>> label = "Triangular soft sail";
        attribute :>> membraneSail = true;
        attribute :>> aerodynamicTrim = false;
        attribute :>> concept = "Triangular woven-polyester sail on mast and boom with sheet control. Reefing/furling is a design option requiring explicit mechanism, mass and fault analysis; battens and reinforcement are not excluded.";
        attribute :>> durability = "Flogging, flutter, chafe, UV/stitching degradation and sheet wear create unattended-maintenance concerns. Durable cloth, battens and anti-chafe design can mitigate them; no lifetime failure is established.";
        attribute :>> energy = "Sheet/winch energy and holding strategy must be measured; self-locking or balanced arrangements may have low static draw. Do not assume a continuously powered servo.";
        attribute :>> sailing = "Both-tack sailing is conventional in principle; actual reefed and unreefed low-Re polars are needed. Compare mass and performance on the same finite-mission basis as both rigid wings.";
        attribute :>> recovery = "Lower membrane mass and negligible sealed cloth volume can help, but model mast/boom buoyancy, immersion drag, trapped water and sheet snagging separately.";
        attribute :>> manufacturing = "Simple sailmaking and repair, low rig-mass potential; requires sailcloth and rigging rather than printing every component. Hull FDM/glass requirement does not prohibit a soft sail.";
        attribute :>> nextEvidence = "Unattended flogging/chafe/UV exposure and sheet fault tests over declared mission hours; autonomous depower and recovery demonstration.";
        metadata rationale : ModelingMetadata::Rationale { text = "Equal development contender for the finite Gorge mission. Compare measured wear, handling, energy, mass and recovery against both rigid wings over the declared exposure; future ocean endurance does not select this rig."; }
    }
    analysis def TradeAssessment {
        subject candidate : Candidate;
        out attribute candidateName : String = candidate.label;
        out attribute gateCount : Integer = SequenceFunctions::size(candidate.gates);
        out attribute knownFailure : Boolean = candidate.gates->ControlFunctions::exists { in gate : Evidence; gate == Evidence::failed };
        out attribute evidenceComplete : Boolean = candidate.gates->ControlFunctions::forAll { in gate : Evidence; gate != Evidence::unknown };
        out attribute qualified : Boolean = gateCount == 7 and candidate.gates->ControlFunctions::forAll { in gate : Evidence; gate == Evidence::passed };
        out attribute requirementVerdict : String = if knownFailure ? "Failed gate" else if qualified ? "Passed declared gates" else "Inconclusive: evidence missing";
        // Explicit development policy, not an inferred failure probability or weighted score.
        return developmentDecision : String = if knownFailure ? "Resolve verified failure before selection" else
        if qualified ? "Eligible for selection; compare validated margins" else
        "Equal development contender for the finite Gorge mission";
        objective assess { require constraint { gateCount == 7 } }
    }
    analysis tailAssessment : TradeAssessment { subject :>> candidate = tailWing; }
    analysis camberAssessment : TradeAssessment { subject :>> candidate = camberedWing; }
    analysis softAssessment : TradeAssessment { subject :>> candidate = softSail; }
    dependency durabilityCriterion from TradeAssessment to BlueDogRequirements::wetMechanicalIntegrity;
    dependency stormWindCriterion from TradeAssessment to BlueDogRequirements::gorgeSurvivalWind;
    dependency progressCriterion from TradeAssessment to BlueDogRequirements::legProgress;
    dependency capsizeCriterion from TradeAssessment to BlueDogRequirements::selfRighting;
    dependency controlCriterion from TradeAssessment to BlueDogRequirements::capsizeControlRecovery;
    dependency liftCriterion from TradeAssessment to BlueDogRequirements::liftMass;
    dependency reliabilityCriterion from TradeAssessment to BlueDogRequirements::missionSuccessProbability;
    dependency reliabilityEvidence from TradeAssessment to BlueDogRequirements::reliabilityEvidence;
    dependency architectureScope from Candidate to BlueDog::Architecture::HullAndRig;
    dependency failureReview from TradeAssessment to BlueDogDFMEA::starter::sailJam;

    part def RigBody {
        doc /* Input contract for the next geometry-based capsize model. Boat-fixed
         * x forward, y port, z up; all lengths m, mass kg, volume m3, time s.
         * Geometry must resolve wetted shape at each heel/pitch/trim; these scalar
         * properties alone do not establish a righting curve. */
        attribute component : String;
        attribute dryMassKg : Real;
        attribute dryCG : Real [3] ordered nonunique;
        attribute sealedVolumeM3 : Real;
        attribute sealedVolumeCentroid : Real [3] ordered nonunique;
        attribute floodableVolumeM3 : Real;
        attribute retainedWaterMassKg : Real;
        attribute retainedWaterCG : Real [3] ordered nonunique;
        attribute fillTimeS : Real;
        attribute drainTimeS : Real;
        attribute geometryReference : String;
        attribute geometryEvidenceAccepted : Boolean default false;
    }
    public import MarineHydrostatics::BuoyancyMomentSensitivity;
    analysis buoyancyIllustration {
        doc /* Ten litres fully immersed at +/-1 m horizontal lever in freshwater.
         * This is a sensitivity example, not a candidate volume or predicted GZ. */
        out attribute positiveMomentNm : Real = BuoyancyMomentSensitivity(0.01,1,1000);
        out attribute negativeMomentNm : Real = BuoyancyMomentSensitivity(0.01,-1,1000);
    }
    dependency geometryForRecovery from RigBody to BlueDogRequirements::selfRighting;
}

package BlueDogConceptCredibility {
    private import ScalarValues::*;
    part policy {
        attribute minimumUnderwaterAspectRatio : Real = 2;
        attribute rudderStockChordFraction : Real = 0.5;
        attribute rudderLoadChordFraction : Real = 0.25;
        doc /* The geometry rotates about mid-chord. Use the attached-flow
         * symmetric-section quarter-chord force location for the provisional
         * torque arm, rather than an independent 2-percent balance credit.
         * https://www1.grc.nasa.gov/beginners-guide-to-aeronautics/aerodynamic-center/
         * Measured hinge moments and stalled/reversed-flow loads remain open. */
        attribute appendageClearanceM : Real = 0.02;
        doc /* Provisional screening allocations, not universal hydrodynamic limits.
         * AR >= 2 excludes squat foils from the simple finite-wing correction;
         * it does not validate that correction at AR=2. Both keel and rudder
         * need section/finite-span evidence before design acceptance.
         * 20 mm is a provisional rigid-geometry separation, not a deflection
         * or debris allowance. The current architecture has no aft outrigger:
         * rudder stock must be at or forward of the transom. A bracket concept
         * must explicitly add its structure, mass and loads before relaxing this.
         * Theory context: https://ntrs.nasa.gov/citations/19930085047 .
         * That source motivates a domain screen; it does not prescribe AR=2. */
    }
    part passagePolicy {
        attribute durationMultiplier : Real = 1.25;
        attribute delayHours : Real = 6;
        attribute batteryInstalledWhM3 : Real = 200000;
        attribute equipmentInstalledKgM3 : Real = 500;
        attribute usableHullVolumeFraction : Real = 0.5;
        doc /* Provisional selected-window allowances: 25 percent sailing-time
         * allowance plus six hours for traffic/weather delay; no deadline.
         * Battery allocation 200 Wh/litre includes pack enclosure; equipment
         * density 0.5 kg/litre includes installation space. Only half the hull
         * void is credited to account for access, taper and segregation.
         * These are not catalog data or calibrated probabilities. Sensitivity
         * cases must test them; actual equipment and CAD fit remain open. */
    }
    analysis Inputs {
        out attribute values : Real [5] ordered nonunique = (passagePolicy.durationMultiplier,passagePolicy.delayHours,passagePolicy.batteryInstalledWhM3,passagePolicy.equipmentInstalledKgM3,passagePolicy.usableHullVolumeFraction);
    }
    analysis SensitivityInputs {
        doc /* One-at-a-time engineering probes, not probability distributions.
         * No probe changes the nominal search constraints. Recovery samples
         * are sparse diagnostics, never dynamic self-righting qualification. */
        out attribute durationMultiplier : Real [3] ordered nonunique = (1,1.25,1.5);
        out attribute delayHours : Real [3] ordered nonunique = (0,6,12);
        out attribute batteryInstalledWhM3 : Real [3] ordered nonunique = (150000,200000,250000);
        out attribute equipmentInstalledKgM3 : Real [3] ordered nonunique = (250,500,750);
        out attribute usableHullVolumeFraction : Real [3] ordered nonunique = (0.35,0.5,0.65);
        out attribute minimumUnderwaterAspectRatio : Real [3] ordered nonunique = (1.5,2,3);
        out attribute recoveryProbeHeels : Real [6] ordered nonunique = (-150,-90,-30,30,90,150);
    }
    dependency enduranceScope from passagePolicy to BlueDogRequirements::multiDayEndurance;
    dependency reserveScope from passagePolicy to BlueDogRequirements::lowEnergyRecovery;
    dependency packagingScope from passagePolicy to BlueDogRequirements::transportability;
    dependency steeringScope from policy to BlueDogRequirements::navigationAndControl;
    dependency handlingScope from policy to BlueDogRequirements::transportability;
    dependency structureScope from policy to BlueDogStructure::structuralIntegrity;
    comment remainingAcceptanceGaps /* Geometry screening is necessary but insufficient.
     * Candidate voyage energy (including reserve and weather delays), component
     * volume/installation space, real foil polars and stall/ventilation,
     * rudder stock/bearings and joints, fatigue/slamming, dynamic recovery and
     * packaging of 250 mm printed segments remain acceptance work.
     * Do not promote coarseFeasible to a credible or mission-qualified design.
     * Report hull length separately from the complete operating envelope;
     * the owner-selected challenge limit is 1.2 m overall. */
}

package BlueDogSizingEvidence {
    private import ScalarValues::*;
    part def Scenario {
        attribute label : String;
        attribute numericallyBalanced : Boolean;
        attribute operatingMargins : Real [1..*] ordered nonunique;
        attribute structuralMargins : Real [1..*] ordered nonunique;
        attribute routeMargins : Real [1..*] ordered nonunique;
        attribute restoringMomentsNm : Real [1..*] ordered nonunique;
        attribute missingPitchRoots : Integer;
        attribute pitchUnstableSamples : Integer;
        attribute diagnosticControlCases : Integer;
        attribute easterlyHours : Real;
        attribute westerlyHours : Real;
        attribute massKg : Real;
        attribute evidenceAccepted : Boolean;
        attribute acceptanceRouteMargins : Real [1..*] ordered nonunique default = routeMargins;
        attribute operatingScreensPass : Boolean = numericallyBalanced and
        operatingMargins->ControlFunctions::forAll { in x : Real; x >= -0.0001 } and
        structuralMargins->ControlFunctions::forAll { in x : Real; x >= -0.0001 } and
        acceptanceRouteMargins->ControlFunctions::forAll { in x : Real; x >= -0.0001 };
        attribute sampledRollPositive : Boolean = missingPitchRoots == 0 and
        restoringMomentsNm->ControlFunctions::forAll { in x : Real; x > 0 };
        doc /* Recorded numerical evidence only. Route durations from diagnostic
         * energy-unconstrained controls are not sustained-operation claims.
         * sampledRollPositive does not assert pitch stability or dynamic recovery.
         * evidenceAccepted is an independent review disposition, never inferred
         * from numerical convergence or these screening predicates. */
    }
    analysis def Review {
        subject scenario : Scenario;
        out attribute operatingScreensPass : Boolean = scenario.operatingScreensPass;
        out attribute sampledRollPositive : Boolean = scenario.sampledRollPositive;
        out attribute evidenceAccepted : Boolean = scenario.evidenceAccepted;
        metadata rationale : ModelingMetadata::Rationale { text = "Recorded margins are inspected with explicit tolerances. The numerical model omits physical qualification evidence; this analysis is not a verification case."; }
    }
    dependency operatingEvidence from Review to BlueDogRequirements::legProgress;
    dependency durationEvidence from Review to BlueDogRequirements::passageDuration;
    dependency energyEvidence from Review to BlueDogRequirements::lowEnergyRecovery;
    dependency structureEvidence from Review to BlueDogStructure::structuralIntegrity;
    dependency recoveryEvidence from Review to BlueDogRequirements::selfRighting;
}

package BlueDogCoupledSizing {
    private import ScalarValues::*;
    public import MarineMass::*;
    private import BlueDogStructure::material;
    doc /* CAD/mesh metrics supply geometry; native calculations own material mass,
     * center of gravity and engineering loads. All numerical process allocations
     * and aerodynamic discrepancy factors remain provisional evidence inputs. */
    analysis Inputs {
        out attribute designNames : String [*] ordered nonunique = ("length_m", "beam_m", "bottom_depth_m", "deck_height_m", "sail_m2", "sail_AR", "camber_scale", "wing_thickness_scale", "mast_fraction", "mast_x_fraction", "keel_m2", "keel_span_m", "rudder_m2", "rudder_span_m", "rudder_arm_fraction", "ballast_kg", "battery_Wh", "panel_m2", "wing_torque_Nm", "rudder_torque_Nm", "hull_glass_kg_m2", "wing_glass_kg_m2", "keel_glass_kg_m2", "rudder_glass_kg_m2", "hull_rib_pitch_m", "foil_rib_pitch_m", "battery_x_fraction", "battery_z_fraction", "hull_fullness_exponent");
        out attribute referenceDesign : Real [*] ordered nonunique = MarineDesign::DesignVector(BlueDogConfigurations::reference);
        out attribute parameterNames : String [*] ordered nonunique = ("resinGlassRatio", "gearboxEfficiency", "motorEfficiency", "wingNoLoadW", "wingControllerW", "wingMotorHoldingW", "wingMoveFraction", "wingHoldingFraction", "rudderHoldingWPerNm", "rudderMoveFraction", "electronicsW", "solarResourceFactor", "batteryWhKg", "laminateKnockdown", "profileCd", "wingClLimit", "wingLiftScale", "wingDragScale", "wingRateRadS", "rudderRateRadS", "driveKgPerNm", "wingDriveBaseKg", "fixedEquipmentKg", "attachmentKg", "residuaryResistanceFactor", "viscousFormFactor", "foilClLimit", "foilEfficiency", "foilCd", "airNu", "waterNu", "waterDensity", "airDensity", "ballastDensity", "gravity", "loadFactor", "assemblyLimitKg", "panelCoverage", "elevatedEquipmentKg", "elevatedEquipmentXFraction", "elevatedEquipmentAboveDeckM");
        out attribute parameterValues : Real [*] ordered nonunique = MarineDesign::ParametersVector(BlueDogConfigurations::assumptions);
        out attribute materialValues : Real [*] ordered nonunique = (material.tapeWidth, material.printTile, material.tapeDryMass, material.petgDensity, material.hullPrintWall, material.finishingMass, material.ribHeight, material.glassDensity, material.epoxyDensity, material.foilPrintWall);
    }

    dependency manufacturing from MassProperties to BlueDogStructure::hybridConstruction;
    dependency handling from MassProperties to BlueDogRequirements::liftMass;
    dependency geometryRecovery from MassProperties to BlueDogRequirements::selfRighting;
}

package BlueDogCoupledOperation {
    private import ScalarValues::*;
    public import MarineSailing::*;
    public import MarineStructures::*;
    public import MarineCourse::*;
    doc /* Quasi-steady force balance. VSPAERO supplies inviscid CL/CDi/CMy;
     * discrepancy factors and viscous drag remain provisional model inputs.
     * Hydrostatic heave/pitch and mast-trim geometry are external geometry solves.
     * No wave-motion, dynamic planing, separated-flow or dynamic recovery claim. */
    analysis Inputs {
        doc /* Named numerical roles for the finite-voyage search. Residuals are
         * normalized by the sailing calculations; nonnegative margins pass.
         * Daily energy balance is diagnostic, not a Gorge constraint. */
        out attribute equilibriumOutputs : String [4] ordered nonunique = ("surgeResidual", "swayResidual", "yawResidual", "rollResidual");
        out attribute staticMarginOutputs : String [11] ordered nonunique = ("wingLiftMargin", "keelLiftMargin", "rudderLiftMargin", "keelAngleMargin", "rudderAngleMargin", "wingDriveMargin", "rudderDriveMargin", "froudeMargin", "wingReMargin", "keelReMargin", "rudderReMargin");
        out attribute peakMarginOutput : String = "peakMargin";
        out attribute resistanceMarginOutputs : String [19] ordered nonunique = ("delftResistanceMargin", "delftDomain4", "delftDomain5", "delftDomain6", "delftDomain7", "delftDomain8", "delftDomain9", "delftDomain10", "delftDomain11", "delftDomain12", "delftDomain13", "delftDomain14", "delftDomain15", "delftDomain16", "delftDomain17", "delftDomain18", "delftDomain19", "delftDomain20", "delftDomain21");
        out attribute maximumOverallLengthM : Real = GorgeChallenge::maximumOverallLength / (1 [SI::m]);
        out attribute challengeRequiresEastProgress : Boolean = BlueDogWeather::policy.challengeRequiresEastProgress;
        out attribute allSeasonRequiresEastProgress : Boolean = BlueDogWeather::policy.allSeasonRequiresEastProgress;
        out attribute windSpeeds : Real [2] ordered nonunique = BlueDogStudyPlan::operatingCoverage.windSpeeds;
        out attribute stateLower : Real [6] ordered nonunique = BlueDogStudyPlan::operatingCoverage.stateLower;
        out attribute stateUpper : Real [6] ordered nonunique = BlueDogStudyPlan::operatingCoverage.stateUpper;
        out attribute leewardHeading : Real [2] ordered nonunique = BlueDogStudyPlan::operatingCoverage.leewardHeading;
        out attribute coarseTrims : Real [2] ordered nonunique = BlueDogStudyPlan::operatingCoverage.coarseTrims;
        out attribute coarseHeels : Real [8] ordered nonunique = BlueDogStudyPlan::operatingCoverage.coarseHeels;
        out attribute recoveryTrims : Real [4] ordered nonunique = BlueDogStudyPlan::operatingCoverage.recoveryTrims;
        out attribute recoveryDensities : Real [2] ordered nonunique = BlueDogStudyPlan::operatingCoverage.recoveryDensities;
        out attribute recoveryHeels : Real [3] ordered nonunique = BlueDogStudyPlan::operatingCoverage.recoveryHeels;
        out attribute progressSearchReserve : Real = BlueDogStudyPlan::operatingCoverage.progressSearchReserve;

        doc /* Search brackets are numerical/domain limits, not new vessel requirements.
         * Aspect/camber are limited by the VSPAERO interpolation grid; thickness
         * remains a geometric sensitivity without validated viscous-drag response. */
        out attribute designLower : Real [29] ordered nonunique = MarineDesign::DesignVector(BlueDogConfigurations::lowerBracket);
        out attribute designUpper : Real [29] ordered nonunique = MarineDesign::DesignVector(BlueDogConfigurations::upperBracket);
        doc /* Search-only mesh-resolution reserves, not vessel requirements.
         * Raw native domain margins remain unchanged for independent replay.
         * Cp and B/L reserves exceed the observed resolution-12 to -16 shifts
         * (0.00175 and 0.00271); remaining non-invariant coordinates receive
         * provisional numerical reserves and still require finer validation.
         * Order: positive resistance, Fn low/high, LCB low/high, Cp low/high,
         * volume/area low/high, B/L low/high, LCB/LCF low/high,
         * volume/length low/high, Cm low/high, B/T low/high. */
        // Search-only mesh/replay reserve: cycleMargin is daily net Wh / 100.
        // 0.005 therefore reserves 0.5 Wh/day; it is not a physical uncertainty allowance.
        out attribute cycleEnergySearchReserve : Real = 0.005;
        out attribute resistanceDomainReserve : Real [19] ordered nonunique = (0,0.002,0.004,0,0,0.003,0.003,0.003,0.003,0.004,0.004,0,0,0.002,0.002,0.002,0.002,0.15,0.15);
        out attribute routeParameters : Real [7] ordered nonunique = (0.95,0.5,1.0,TransGorgeCourse::policy.referenceLegLengthM,0,0.5,1.0);
        out attribute structureValues : Real [12] ordered nonunique = (BlueDogStructure::material.laminateModulus, BlueDogStructure::material.laminateAllowable, BlueDogStructure::material.pressure, BlueDogStructure::material.tipProofForce, BlueDogStructure::material.minimumFreeboard, BlueDogStructure::material.reserveFraction, BlueDogStructure::material.launchDepth-BlueDogStructure::material.bottomClearance, BlueDogStructure::material.appendageDeflectionFraction, BlueDogStructure::material.hullDeflectionFraction, BlueDogStructure::material.panelDeflectionFraction, BlueDogConceptCredibility::policy.minimumUnderwaterAspectRatio, BlueDogConceptCredibility::policy.appendageClearanceM);
    }

    dependency sustained from Evaluate to BlueDogRequirements::sustainedEnergyFeasibility;
    dependency progress from Evaluate to BlueDogRequirements::legProgress;
    dependency control from Evaluate to BlueDogRequirements::capsizeControlRecovery;

    dependency strength from DesignMargins to BlueDogStructure::structuralIntegrity;
    dependency handling from DesignMargins to BlueDogRequirements::liftMass;

    dependency routeProgress from Route to BlueDogRequirements::legProgress;
    dependency routeTime from Route to BlueDogRequirements::passageDuration;
}

package BlueDogCoupledUncertainty {
    private import ScalarValues::*;
    doc /* Explicit engineering sensitivity brackets, not calibrated probability
     * distributions or qualified tolerances. They expose dependence on missing
     * material/actuator/polar/environment evidence; they do not replace it. */
    analysis Inputs {
        out attribute nominal : Real [41] ordered nonunique = BlueDogCoupledSizing::Inputs.parameterValues;
        out attribute construction : Real [41] ordered nonunique = (1..41)->ControlFunctions::collect { in i : Integer; if i == 1 ? 1.2 else if i == 13 ? 120 else if i == 14 ? 0.7 else if i == 21 ? 0.225 else if i == 23 ? 3 else BlueDogCoupledSizing::Inputs.parameterValues#(i) };
        out attribute aerodynamic : Real [41] ordered nonunique = (1..41)->ControlFunctions::collect { in i : Integer; if i == 15 ? BlueDogAerodynamicPolicy::stress.profileCd else if i == 16 ? BlueDogAerodynamicPolicy::stress.clLimit else if i == 17 ? BlueDogAerodynamicPolicy::stress.liftScale else if i == 18 ? BlueDogAerodynamicPolicy::stress.dragScale else BlueDogCoupledSizing::Inputs.parameterValues#(i) };
        out attribute hydrodynamic : Real [41] ordered nonunique = (1..41)->ControlFunctions::collect { in i : Integer; if i == 25 ? 1.3 else BlueDogCoupledSizing::Inputs.parameterValues#(i) };
        out attribute energy : Real [41] ordered nonunique = (1..41)->ControlFunctions::collect { in i : Integer; if i == 2 ? 0.25 else if i == 3 ? 0.7 else if i == 5 ? 0.15 else if i == 7 ? 0.05 else if i == 8 ? 0.95 else if i == 10 ? 0.1 else if i == 11 ? 5.5 + BlueDogWindEquipment::challenge.busPowerW else if i == 12 ? 0.45 else BlueDogCoupledSizing::Inputs.parameterValues#(i) };
        out attribute combined : Real [41] ordered nonunique = (1..41)->ControlFunctions::collect { in i : Integer; if i == 25 ? 1.3 else if i == 1 ? 1.2 else if i == 13 ? 120 else if i == 14 ? 0.7 else if i == 21 ? 0.225 else if i == 23 ? 3 else if i == 15 ? BlueDogAerodynamicPolicy::stress.profileCd else if i == 16 ? BlueDogAerodynamicPolicy::stress.clLimit else if i == 17 ? BlueDogAerodynamicPolicy::stress.liftScale else if i == 18 ? BlueDogAerodynamicPolicy::stress.dragScale else if i == 2 ? 0.25 else if i == 3 ? 0.7 else if i == 5 ? 0.15 else if i == 7 ? 0.05 else if i == 8 ? 0.95 else if i == 10 ? 0.1 else if i == 11 ? 5.5 + BlueDogWindEquipment::challenge.busPowerW else if i == 12 ? 0.45 else BlueDogCoupledSizing::Inputs.parameterValues#(i) };
        out attribute nominalRoute : Real [7] ordered nonunique = (0.95,0.5,1,TransGorgeCourse::policy.referenceLegLengthM,0,0.5,1);
        out attribute adverseRoute : Real [7] ordered nonunique = (0.90,0.75,1.25,TransGorgeCourse::policy.referenceLegLengthM,0,0.5,1);
    }
    dependency materialEvidence from Inputs to BlueDogStructure::structuralIntegrity;
    dependency energyEvidence from Inputs to BlueDogRequirements::sustainedEnergyFeasibility;
    dependency routeEvidence from Inputs to BlueDogRequirements::cruiseEvidence;
}

package BlueDogStructuralBasis {
    private import ScalarValues::*;
    doc /* Provisional construction and numerical screening basis. No values here are
     * asserted to follow uniquely from the Gorge challenge. */
    analysis def Inputs {
        doc /* PETG density: Prusament PETG TDS 2021/10, revision 2022-02-16, 1.27 g/cm3.
         * Epoxy density: WEST SYSTEM 105/206 TDS 2014, cured specific gravity 1.18.
         * Glass density 2550 kg/m3 and 1:1 retained mixed-resin/dry-glass mass ratio
         * are project assumptions. 10 GPa and 50 MPa are unverified provisional
         * analysis inputs, not minimum material qualification requirements.
         * 200 g/m2 ply, PETG wall/infill, finishing and seam budgets are process
         * assumptions. Resin waste in cups/tools is excluded from vessel mass. */
        out attribute qualified : Boolean = false;
        doc /* Screening values below remain unchanged to preserve the meaning of existing
         * sizing runs. Deflection fractions, pressure/proof loads, freeboard, reserve,
         * launch depth and tile size are provisional study controls, not challenge minima.
         * Acceptance uses measured material bounds and validated functional/site limits.
         * A passing study does not verify a requirement; re-size when evidence changes. */
        out attribute petgDensity : Real = 1270;
        out attribute glassDensity : Real = 2550;
        out attribute epoxyDensity : Real = 1180;
        out attribute resinGlassRatio : Real = 1;
        out attribute laminateModulus : Real = 10000000000;
        out attribute laminateAllowable : Real = 50000000;
        out attribute hullPrintWall : Real = 0.0008;
        out attribute foilPrintWall : Real = 0.0004;
        out attribute ribHeight : Real = 0.01;
        out attribute foilInfill : Real = 0.08;
        out attribute foilThicknessRatio : Real = 0.12;
        out attribute finishingMass : Real = 0.10;
        out attribute tapeWidth : Real = 0.03;
        out attribute tapeDryMass : Real = 0.20;
        out attribute printTile : Real = 0.23;
        out attribute minimumFreeboard : Real = 0.05;
        out attribute reserveFraction : Real = 1;
        out attribute launchDepth : Real = 1.5;
        out attribute bottomClearance : Real = 0.3;
        out attribute pressure : Real = 10000;
        out attribute tipProofForce : Real = 100;
        out attribute appendageDeflectionFraction : Real = 0.02;
        out attribute hullDeflectionFraction : Real = 0.005;
        out attribute panelDeflectionFraction : Real = 0.01;
    }

    dependency constructionChoice from Inputs to BlueDogStructure::hybridConstruction;
    dependency studyPurpose from Inputs to BlueDogStructure::structuralIntegrity;
}

package BlueDogSurfaceEnvironment {
    private import ScalarValues::*;
    part policy {
        // Prescribed response sensitivities, not identified vessel RAOs.
        attribute motionStudyHsM : Real = 0.4;
        attribute motionStudyPeriodS : Real = 3;
        attribute heaveGain : Real = 1;
        attribute slopeGain : Real = 1;
        attribute motionPhaseCount : Integer = 32;
        attribute maximumMotionAngleRad : Real = 0.35;
        attribute referenceHeightM : Real = 10;
        attribute roughnessM : Real = 0.0002;
        attribute minimumProfileHeightM : Real = 0.05;
        attribute stripCount : Integer = 8;
        attribute waveResistanceCoefficient : Real = 1;
        attribute effectiveFetchM : Real = 8000;
        attribute waveGrowthHours : Real = 2;
        attribute wakeHeightM : Real = 0.3;
        attribute wakePeriodS : Real = 2;
        attribute wakeDurationS : Real = 120;
        attribute wakeRadiusM : Real = 300;
        metadata rationale : ModelingMetadata::Rationale { text = "The synthetic mission wind is explicitly interpreted at 10 m, not claimed to be a corrected NOAA station observation. Neutral roughness is a hypothesis; test 0.00002 to 0.002 m. Eight equal-area wing strips use the existing finite-wing polar locally, an approximate treatment of shear without lifting-line redistribution. Fetch 8 km (sensitivity 3 and 15 km) is effective open-water fetch, not a chart-derived ray. SMB deep-water fetch growth supplies sea height/period; two-hour relaxation supplies memory. Wave/current action transport is an entry-from-still-water sensitivity, not a measured Gorge current gradient. Coefficient 1 (sensitivity 0.5 and 2) sets uncalibrated added resistance. Wake height, duration and radius are scenario hypotheses attached to nearby powered traffic, not measured wake propagation."; }
        metadata issue : ModelingMetadata::Issue { text = "Prescribed wave-following heave and slope response is a sensitivity, not identified seakeeping RAOs. No wave-phase control, slamming load, wave shielding or viscous stall prediction. Hs is not a maximum wave. A 2Hs individual-wave screen has crest/trough amplitude Hs and reports possible contact/ventilation, not failure: Phase-resolved motion screens now report relative clearance; response gains remain unvalidated. Monte Carlo counts are conditional synthetic sensitivity results, not mission reliability estimates."; }
        comment motionMethod /* Mean-water wind datum is retained. The wave and vessel
         * are translated together; local water elevation is used only for contact.
         * Test fixed response (0,0), heave following (1,0), and slope following
         * (1,1). These are hypotheses, not bounds on resonant response. Independent
         * deterministic component phases sample mixed seas; no resolved spectrum.
         * https://www.orcina.com/webhelp/OrcaFlex/Content/html/Vesseltheory,RAOsandphases.htm */
        comment sources /* Neutral profile: https://www.nrel.gov/docs/fy21osti/78412.pdf
         * SMB equations: https://cosefm.cee.wisc.edu/CEE514_Coastal_Engineering/Online_Solver/Wind_Waves.html
         * Wave/current and encounter conventions: https://www.orcina.com/webhelp/OrcaFlex/Content/html/Vesseltheory,Wavedriftandsumfrequencyloads.htm */
    }
    analysis Inputs {
        out attribute motionSea : Real [2] ordered nonunique = (policy.motionStudyHsM,policy.motionStudyPeriodS);
        out attribute motion : Real [4] ordered nonunique = (policy.heaveGain,policy.slopeGain,policy.motionPhaseCount,policy.maximumMotionAngleRad);
        out attribute wind : Real [4] ordered nonunique = (policy.referenceHeightM,policy.roughnessM,policy.minimumProfileHeightM,policy.stripCount);
        out attribute sea : Real [7] ordered nonunique = (policy.effectiveFetchM,policy.waveGrowthHours,policy.waveResistanceCoefficient,policy.wakeHeightM,policy.wakePeriodS,policy.wakeDurationS,policy.wakeRadiusM);
    }
    dependency windPerformance from policy to BlueDogRequirements::legProgress;
    dependency windEnvelope from policy to BlueDogRequirements::gorgeWind;
    dependency waves from policy to BlueDogRequirements::gorgeWaves;
    dependency currentInteraction from policy to BlueDogRequirements::gorgeCurrent;
    dependency recovery from policy to BlueDogRequirements::capsizeControlRecovery;
}

package BlueDogWavePerformance {
    private import ScalarValues::*;
    part policy {
        attribute phaseCount : Integer = 16;
        attribute smallWaveHeightM : Real = 0.04;
        attribute maximumMotionRad : Real = 0.20;
        attribute maximumSteepness : Real = 0.05;
        attribute viscousDampingRatio : Real = 0.05;
        attribute maximumHeaveDraftRatio : Real = 0.5;
        attribute maximumMeanHeelDeg : Real = 25;
        attribute meshResolution : Integer = 5;
        attribute refinedMeshResolution : Integer = 9;
        attribute meshTolerance : Real = 0.15;
        attribute phaseTolerance : Real = 0.02;
        metadata rationale : ModelingMetadata::Rationale { text = "Fixed 1.4 m geometry. Linear potential-flow response includes heave, roll and pitch, with mesh-derived distributed component inertia and explicit 5 percent additional damping hypothesis. Mean wetted geometry is upright; mean heel limited to 25 degrees as an engineering screen, not a validation result. Wave phase loads are averaged while controls stay fixed during each cycle; SciPy solves mean surge, sway, yaw and roll balance and maximizes VMG. Added wave resistance retains the existing coefficient sensitivity once only, separately from first-order BEM response; it is not validated second-order drift. No surge/sway/yaw wave-frequency response, slamming or separated-flow claim."; }
        metadata issue : ModelingMetadata::Issue { text = "Equipment intrinsic inertia and viscous damping need identification. Rotating-wing inertia is evaluated at reference trim. Linear-response coverage is provisional. Mean-water neutral wind profile is rejected below its minimum supported height, rather than relabeled as a moving-surface profile. No aerodynamic extrapolation earns accepted performance. Mission seas outside the solved regular-wave grid are coverage failures, not physical mission failures."; }
        comment sources /* https://capytaine.org/stable/user_manual/problem_setup.html
         * https://capytaine.org/stable/user_manual/hydrostatics.html
         * https://capytaine.org/stable/user_manual/post_pro.html */
    }
    analysis Inputs {
        out attribute settings : Real [10] ordered nonunique = (policy.phaseCount,policy.smallWaveHeightM,policy.maximumMotionRad,policy.maximumSteepness,policy.viscousDampingRatio,policy.maximumHeaveDraftRatio,policy.maximumMeanHeelDeg,policy.meshResolution,policy.meshTolerance,policy.phaseTolerance);
        out attribute periods : Real [3] ordered nonunique = (2,3,5);
        out attribute speeds : Real [5] ordered nonunique = (0,0.75,1.5,2.25,3);
        out attribute directions : Real [4] ordered nonunique = (0,90,180,270);
        out attribute refinement : Real = policy.refinedMeshResolution;
    }
    dependency progress from policy to BlueDogRequirements::legProgress;
    dependency environment from policy to BlueDogRequirements::gorgeWaves;
    dependency recovery from policy to BlueDogRequirements::capsizeControlRecovery;
}

package BlueDogWeather {
    private import ScalarValues::*;
    part policy {
        doc /* Weather-window challenge; winter development tests and eventual
         * year-round unattended operation are separate profiles. West is the
         * representative challenge direction, not an assured forecast. */
        attribute challengeRequiresEastProgress : Boolean = false;
        attribute allSeasonRequiresEastProgress : Boolean = true;
        attribute firstYear : Integer = 2015;
        attribute lastYear : Integer = 2024;
        attribute warmMonths : Integer [5] ordered = (5,6,7,8,9);
        attribute winterMonths : Integer [5] ordered = (11,12,1,2,3);
        attribute eastSector : Real [2] ordered = (45,135);
        attribute westSector : Real [2] ordered = (225,315);
        attribute lightWindThreshold : Real = 2;
        attribute precedingWestHours : Integer = 6;
        attribute windowHours : Integer = 72;
        attribute probabilitySweep : Real [11] ordered = (0,0.1,0.2,0.3,0.4,0.5,0.6,0.7,0.8,0.9,1);
        metadata rationale : ModelingMetadata::Rationale { text = "Owner selected a favorable-weather-window qualifying attempt, with year-round operation later. Sharp and Mass (2004), https://doi.org/10.1175/826.1, supports season-dependent regimes. NOAA ISD-Lite 2015-2024 at KDLS and KTTD supplies descriptive station observations, not a calibrated route or forecast model. Sectors and the 2 m/s light-wind split are analysis bins, not sailing limits. Six preceding westerly hours define a reproducible hindcast selection probe, not a launch authorization. The 72-hour horizon is a fixed historical climatology comparison window only; it is not a passage deadline or launch forecast requirement. Active launch assessment must cover predicted passage, waiting and recovery exposure."; }
        metadata issue : ModelingMetadata::Issue { text = "No accepted east-wind mission probability or weather-success allocation yet. Need along-route wind, forecast-conditioned persistent trajectories, joint current/wave/solar conditions, and failed/held/aborted passage outcomes. Airport heights/exposure differ from the small wing. Winter tests do not inherit summer weights. Storm survival, recovery, traffic and no-intervention rules are not relaxed by frequency weighting."; }
    }
    analysis Inputs {
        out attribute challengeRequiresEastProgress : Boolean = policy.challengeRequiresEastProgress;
        out attribute allSeasonRequiresEastProgress : Boolean = policy.allSeasonRequiresEastProgress;
        out attribute firstYear : Integer = policy.firstYear;
        out attribute lastYear : Integer = policy.lastYear;
        out attribute warmMonths : Integer [5] ordered = policy.warmMonths;
        out attribute winterMonths : Integer [5] ordered = policy.winterMonths;
        out attribute eastSector : Real [2] ordered = policy.eastSector;
        out attribute westSector : Real [2] ordered = policy.westSector;
        out attribute lightWindThreshold : Real = policy.lightWindThreshold;
        out attribute precedingWestHours : Integer = policy.precedingWestHours;
        out attribute windowHours : Integer = policy.windowHours;
        out attribute probabilitySweep : Real [11] ordered = policy.probabilitySweep;
    }
    part def StationSeason {
        attribute station : String;
        attribute season : String;
        attribute expectedHours : Integer;
        attribute observedHours : Integer;
        attribute westHours : Integer;
        attribute eastHours : Integer;
        attribute lightHours : Integer;
        attribute otherHours : Integer;
        attribute unknownHours : Integer;
        attribute selectedWindows : Integer;
        attribute windowsWithEast : Integer;
        attribute incompleteWindows : Integer;
        attribute coveragePercent : Real = 100.0 * observedHours / expectedHours;
        attribute westPercent : Real = 100.0 * westHours / expectedHours;
        attribute eastPercent : Real = 100.0 * eastHours / expectedHours;
        attribute lightPercent : Real = 100.0 * lightHours / expectedHours;
        attribute otherPercent : Real = 100.0 * otherHours / expectedHours;
        attribute unknownPercent : Real = 100.0 * unknownHours / expectedHours;
        attribute eastAmongAxisPercent : Real = if westHours + eastHours > 0 ? 100.0 * eastHours / (westHours + eastHours) else 0;
        attribute eastEncounterPercent : Real = if selectedWindows > 0 ? 100.0 * windowsWithEast / selectedWindows else 0;
        attribute eastEncounterLabel : String = if selectedWindows > 0 ? "Complete windows only; see missing-data bounds" else "Not estimable: no complete windows";
        attribute encounterLowerPercent : Real = if selectedWindows + incompleteWindows > 0 ? 100.0 * windowsWithEast / (selectedWindows + incompleteWindows) else 0;
        attribute encounterUpperPercent : Real = if selectedWindows + incompleteWindows > 0 ? 100.0 * (windowsWithEast + incompleteWindows) / (selectedWindows + incompleteWindows) else 0;
    }
    analysis def RegimeSensitivity {
        subject result : BlueDogSizingEvidence::Scenario;
        out attribute probabilities : Real [11] ordered = policy.probabilitySweep;
        out attribute eligible : Boolean = result.numericallyBalanced and result.diagnosticControlCases == 0 and
        result.operatingMargins->ControlFunctions::forAll { in x : Real; x >= -0.0001 };
        out attribute westPass : Boolean = eligible and result.routeMargins#(4) >= -0.0001 and result.routeMargins#(5) >= -0.0001 and result.routeMargins#(6) >= -0.0001;
        out attribute eastPass : Boolean = eligible and result.routeMargins#(1) >= -0.0001 and result.routeMargins#(2) >= -0.0001 and result.routeMargins#(3) >= -0.0001;
        out attribute coverage : Real [11] ordered nonunique = probabilities->ControlFunctions::collect { in p : Real; MarineWeather::TwoRegimeCoverage(p,westPass,eastPass) };
        out attribute conditionalHours : Real [11] ordered nonunique = probabilities->ControlFunctions::collect { in p : Real; MarineWeather::ConditionalPassageHours(p,westPass,eastPass,result.westerlyHours,result.easterlyHours) };
        doc /* Counterfactual persistent-regime sensitivity over archived fixed geometry.
         * Probabilities are swept, not calibrated from hourly station frequencies.
         * A failed route screen is a failure, not a large finite passage time.
         * Structural and recovery failures remain separate hard failures. */
    }
    analysis primary : RegimeSensitivity { subject :>> result = BlueDogCurrentSizing::nominal; }
    analysis construction : RegimeSensitivity { subject :>> result = BlueDogCurrentSizing::construction; }
    analysis aerodynamic : RegimeSensitivity { subject :>> result = BlueDogCurrentSizing::aerodynamic; }
    analysis hydrodynamic : RegimeSensitivity { subject :>> result = BlueDogCurrentSizing::hydrodynamic; }
    analysis energy : RegimeSensitivity { subject :>> result = BlueDogCurrentSizing::energy; }
    analysis combined : RegimeSensitivity { subject :>> result = BlueDogCurrentSizing::combined; }
    dependency performanceProfile from policy to BlueDogRequirements::cruiseEvidence;
    dependency progressProfile from policy to BlueDogRequirements::legProgress;
    dependency exposureProfile from policy to BlueDogRequirements::passageDuration;
    dependency reliabilityProfile from policy to BlueDogRequirements::missionSuccessProbability;
    dependency energyProfile from policy to BlueDogRequirements::sustainedEnergyFeasibility;
    dependency sailingProfile from policy to BlueDogSailing::PolarVoyageAssessment;
    dependency searchProfile from policy to BlueDogCoupledOperation::Route;
}

package BlueDogWingHeel {
    private import ScalarValues::*;
    analysis sweepInputs {
        doc /* Numerical sensitivity study of the fixed-camber reference wing.
         * World axes: X aft, Y starboard, Z up. Positive heel rotates about +X.
         * Apparent wind is horizontal, from AWA clockwise from the bow.
         * Upright nominal incidence fixes mast trim; heel does not retrim it.
         * R = Rx(heel) Rz(nominalAlpha - AWA) Rx(90 degrees) maps wing to world.
         * Transform wind into wing axes; solve alpha and beta together, then
         * rotate dimensional inviscid forces and moments back to world axes.
         * Moment origin is the root midchord, not the vessel center of gravity. */
        out attribute areaM2 : Real = 1;
        out attribute aspectRatio : Real = 4;
        out attribute speedMps : Real = 5;
        out attribute airDensity : Real = 1.225;
        out attribute kinematicViscosity : Real = 0.000015;
        out attribute mesh : Integer = 24;
        out attribute wakeIterations : Integer = 5;
        out attribute heelDegrees : Real [5] ordered = (-40,-20,0,20,40);
        out attribute apparentWindDegrees : Real [3] ordered = (45,90,135);
        out attribute nominalAlphaDegrees : Real [8] ordered = (-12,-8,-4,0,4,8,12,16);
        metadata rationale : ModelingMetadata::Rationale { text = "Cover the current operating heel bounds and three wind directions. Resolve heel-induced spanwise flow and compare with the provisional cosine projection, holding mast trim fixed for each nominal incidence. Free-air attached-flow sensitivity only; no water surface, hull, mast, stall, gust or dynamic roll model. No automatic replacement of the optimizer polar."; }
    }
    dependency purpose from sweepInputs to BlueDogRequirements::cruiseEvidence;
    dependency approximationUnderReview from sweepInputs to MarineSailing::Evaluate;
    dependency scope from sweepInputs to BlueDogDesignDecisions::aerodynamicScope;
}

package BlueDogAcousticEquipment {
    doc /* Acoustic bench candidates reviewed 2026-10-16. Supplier facts and project allowances are separate. Stand-alone planning assemblies are not complete traffic-safety solutions. No sensing simulation or requirement change. Dependencies identify questions, not satisfaction. See docs/reference/acoustic-sensing.md and its source register.*/
    private import ScalarValues::*;
    part passiveArray {
        doc /* AC-01: four Aquarian H3dX on four Zoom F6 channels, USB to Pi 4B. Shared recorder clock does not establish calibrated channel phase. Project array geometry is unvalidated. Cueing audible targets cannot cover quiet hazards.*/
        attribute id : String = "AC-01";
        attribute hydrophone : String = "Aquarian H3dX";
        attribute channelCount : Real = 4;
        attribute adc : String = "Zoom F6";
        attribute adcAvailableChannels : Real = 6;
        attribute host : String = "Raspberry Pi 4 Model B";
        attribute hydrophoneHeadMassKg : Real = 0.01;
        attribute recorderMassKg : Real = 0.52;
        attribute hydrophonePhantomVoltageV : Real = 48;
        attribute hydrophoneTypicalCurrentA : Real = 0.0012;
        attribute recorderMainUnitOnlyW : Real = 1;
        attribute arrayForeAftM : Real = 0.6;
        attribute arrayAthwartM : Real = 0.3;
        attribute supplierSource : String = "https://www.aquarianaudio.com/AqAudDocs/H3dX_manual.pdf";
        attribute massScope : String = "Head mass excludes cable/plug. Support covers host, four cables/XLR, enclosure, regulator, USB, rigid mount and flow shrouds, not optics or recovery.";
        attribute powerScope : String = "Recorder 1 W is main-unit-only. Nominal 48 V times current is phantom-supply power before feed losses, not power delivered inside the hydrophone or battery input; 5 V 1 A supply rating is not draw.";
        attribute observationBlocker : String = "Calibrate geometry, phase, sound speed and noise. Bearing does not establish metric range/range rate. Source level is unknown; amplitude-only range unsupported. Flow, self-noise, multipath and quiet targets unresolved.";
        attribute recoveryBlocker : String = "Heads may emerge inverted. Shared recorder, host and power not independent recovery.";
        attribute detectionRangeDemonstrated : Boolean = false;
        attribute bearingAccuracyDemonstrated : Boolean = false;
        attribute metricRangeDemonstrated : Boolean = false;
        attribute relativeMotionDemonstrated : Boolean = false;
        attribute latencyDemonstrated : Boolean = false;
        attribute dayNightCoverageDemonstrated : Boolean = false;
        attribute installedBudgetComplete : Boolean = false;
        attribute invertedObservationDemonstrated : Boolean = false;
        attribute independentRecoveryComplete : Boolean = false;
        attribute hardwareSelected : Boolean = false;
        attribute physicalQualification : Boolean = false;
        attribute plannedSampleRateHz : Real = 48000;
        attribute liveStreamingCompatibilityDemonstrated : Boolean = false;
    } part narrowBeamForward {
        doc /* AC-02: Omniscan 450 FS 100 m depth variant with Pi 4B. Narrow single beam builds an image using motion; not multibeam. Instrument range is not target detection evidence.*/
        attribute id : String = "AC-02";
        attribute sonar : String = "Cerulean Omniscan 450 FS, 100 m depth variant";
        attribute host : String = "Raspberry Pi 4 Model B";
        attribute componentMassKg : Real = 0.44;
        attribute supplierMaxPowerW : Real = 10;
        attribute supplyMinV : Real = 10;
        attribute supplyMaxV : Real = 30;
        attribute horizontalBeamDeg : Real = 0.8;
        attribute verticalBeamDeg : Real = 50;
        attribute supplierInstrumentRangeM : Real = 120;
        attribute dataInterface : String = "100Base-T Ethernet";
        attribute supplierSource : String = "https://docs.ceruleansonar.com/c/omniscan-450/specifications";
        attribute observationBlocker : String = "Known motion needed for coverage. Thin weeds, clutter, bubbles, shadowing, update age and above-water hazards unresolved.";
        attribute recoveryBlocker : String = "Mount may emerge inverted. Shared host, Ethernet and power not independent recovery.";
        attribute detectionRangeDemonstrated : Boolean = false;
        attribute bearingAccuracyDemonstrated : Boolean = false;
        attribute metricRangeDemonstrated : Boolean = false;
        attribute relativeMotionDemonstrated : Boolean = false;
        attribute latencyDemonstrated : Boolean = false;
        attribute dayNightCoverageDemonstrated : Boolean = false;
        attribute installedBudgetComplete : Boolean = false;
        attribute invertedObservationDemonstrated : Boolean = false;
        attribute independentRecoveryComplete : Boolean = false;
        attribute hardwareSelected : Boolean = false;
        attribute physicalQualification : Boolean = false;
        attribute narrowBeamAppliesBeyondM : Real = 5;
    } part multibeamForward {
        doc /* AC-03: Sonoptix ECHO with Pi 4B. Supplier instrument range, beams and powers do not establish Blue Dog target detection, tracking or latency.*/
        attribute id : String = "AC-03";
        attribute sonar : String = "Sonoptix ECHO";
        attribute host : String = "Raspberry Pi 4 Model B";
        attribute componentMassKg : Real = 0.75;
        attribute supplierPowerLowW : Real = 5;
        attribute supplierPowerHighW : Real = 25;
        attribute supplierActiveExampleVoltageV : Real = 12;
        attribute supplierActiveExampleCurrentA : Real = 1.2;
        attribute supplyMinV : Real = 9;
        attribute supplyMaxV : Real = 28;
        attribute beamCount : Real = 256;
        attribute horizontal400kHzDeg : Real = 90;
        attribute horizontal700kHzDeg : Real = 120;
        attribute verticalBeamDeg : Real = 20;
        attribute instrumentRange400kHzM : Real = 200;
        attribute instrumentRange700kHzM : Real = 30;
        attribute dataInterface : String = "Ethernet";
        attribute supplierSource : String = "https://bluerobotics.com/store/sonars/imaging-sonars/sonoptix-echo/";
        attribute observationBlocker : String = "Beams do not establish target probability, thin-strand resolution or swept-volume clearance. Reverberation, bubbles, attitude, masking and latency need measurement.";
        attribute recoveryBlocker : String = "Mount may emerge inverted. Shared host, Ethernet and power not independent recovery.";
        attribute detectionRangeDemonstrated : Boolean = false;
        attribute bearingAccuracyDemonstrated : Boolean = false;
        attribute metricRangeDemonstrated : Boolean = false;
        attribute relativeMotionDemonstrated : Boolean = false;
        attribute latencyDemonstrated : Boolean = false;
        attribute dayNightCoverageDemonstrated : Boolean = false;
        attribute installedBudgetComplete : Boolean = false;
        attribute invertedObservationDemonstrated : Boolean = false;
        attribute independentRecoveryComplete : Boolean = false;
        attribute hardwareSelected : Boolean = false;
        attribute physicalQualification : Boolean = false;
    } part planning {
        doc /* Unmeasured project allowances. Recorder power includes phantom and four microphones once. Shared host replacement requires explicit reconciliation; do not subtract a whole support assembly. Mass excludes optics, recovery and batteries. Storage, bandwidth and thermal performance unresolved.*/
        attribute recorderWithPhantomLowW : Real = 1.5;
        attribute recorderWithPhantomHighW : Real = 3;
        attribute hostLowW : Real = 3;
        attribute hostHighW : Real = 6;
        attribute conversionEfficiency : Real = 0.9;
        attribute passiveSupportMassKg : Real = 0.45;
        attribute activeSupportMassKg : Real = 0.3;
    }
    analysis Budget {
        doc /* Component/project arithmetic only. Mass remainder is not free payload. Active upper cases combine supplier maxima and host planning high, not measured average. Maximum power alone cannot reject an average-energy allocation. Ethernet, heating/cleaning and recovery unallocated.*/
        out attribute passiveHydrophoneHeadsKg : Real = passiveArray.channelCount*passiveArray.hydrophoneHeadMassKg;
        out attribute passiveNominalPhantomSupplyW : Real = passiveArray.channelCount*passiveArray.hydrophonePhantomVoltageV*passiveArray.hydrophoneTypicalCurrentA;
        out attribute passivePlanningMassKg : Real = passiveHydrophoneHeadsKg+passiveArray.recorderMassKg+planning.passiveSupportMassKg;
        out attribute passivePlanningRailLowW : Real = planning.recorderWithPhantomLowW+planning.hostLowW;
        out attribute passivePlanningRailHighW : Real = planning.recorderWithPhantomHighW+planning.hostHighW;
        out attribute passivePlanningBatteryLowW : Real = passivePlanningRailLowW/planning.conversionEfficiency;
        out attribute passivePlanningBatteryHighW : Real = passivePlanningRailHighW/planning.conversionEfficiency;
        out attribute narrowBeamPlanningMassKg : Real = narrowBeamForward.componentMassKg+planning.activeSupportMassKg;
        out attribute multibeamPlanningMassKg : Real = multibeamForward.componentMassKg+planning.activeSupportMassKg;
        out attribute narrowBeamMaxPlusHostHighW : Real = narrowBeamForward.supplierMaxPowerW+planning.hostHighW;
        out attribute multibeamMaxPlusHostHighW : Real = multibeamForward.supplierPowerHighW+planning.hostHighW;
        out attribute multibeamSupplierActiveExampleW : Real = multibeamForward.supplierActiveExampleVoltageV*multibeamForward.supplierActiveExampleCurrentA;
        out attribute installedBudgetComplete : Boolean = false;
        out attribute physicalQualification : Boolean = false;
    }
    dependency trafficQuestion from passiveArray to BlueDogRequirements::trafficSafety;
    dependency trackQuestion from passiveArray to BlueDogRequirements::trafficTracking;
    dependency underwaterQuestion from multibeamForward to BlueDogRequirements::trafficSafety;
    dependency integrationBudget from Budget to BlueDogIntegratedCandidate::hypothesis;
}
package BlueDogEnergyExamples {
    private import SI::*;
    doc /* Illustrative system budget with an explicit provisional wired wind-sensor allocation.
     * Other equipment loads remain synthetic; none are accepted measurements. A zero payload represents absent optional equipment, not an
     * unmeasured installed load. Solar resource and battery capacity are illustrative.
     * Recovery motor is excluded from qualifying sailing loads; its reserve is protected.
     */
    part sailing : BlueDogEnergy::LoadBudget {
        part controller :> loads {
            attribute :>> label = "Guidance and mission computer";
            attribute :>> activePower default = 2 [W];
            attribute :>> idlePower default = 0.8 [W];
            attribute :>> activeFraction default = 1;
            attribute :>> conversionEfficiency default = 0.9;
            attribute :>> uncertaintyFactor default = 1.15;
        }
        part navigation :> loads {
            attribute :>> label = "Position and attitude sensors";
            attribute :>> activePower default = 0.5 [W];
            attribute :>> idlePower default = 0.1 [W];
            attribute :>> activeFraction default = 1;
            attribute :>> conversionEfficiency default = 0.9;
            attribute :>> uncertaintyFactor default = 1.15;
        }
        part wind :> loads {
            attribute :>> label = "Calypso ULP Wired Mini with interface allowance";
            attribute :>> activePower default = BlueDogWindEquipment::challenge.busPowerW * 1 [W];
            attribute :>> idlePower default = BlueDogWindEquipment::challenge.busPowerW * 1 [W];
            attribute :>> activeFraction default = 1;
            attribute :>> conversionEfficiency default = 1;
            attribute :>> uncertaintyFactor default = 1;
        }
        part traffic :> loads {
            attribute :>> label = "Traffic sensing";
            attribute :>> activePower default = 1 [W];
            attribute :>> idlePower default = 0.2 [W];
            attribute :>> activeFraction default = 1;
            attribute :>> conversionEfficiency default = 0.9;
            attribute :>> uncertaintyFactor default = 1.15;
        }
        part sail :> loads {
            attribute :>> label = "Sail actuator";
            attribute :>> activePower default = 8 [W];
            attribute :>> idlePower default = 0.05 [W];
            attribute :>> activeFraction default = 0.02;
            attribute :>> conversionEfficiency default = 0.9;
            attribute :>> uncertaintyFactor default = 1.15;
        }
        part steering :> loads {
            attribute :>> label = "Steering actuator";
            attribute :>> activePower default = 6 [W];
            attribute :>> idlePower default = 0.05 [W];
            attribute :>> activeFraction default = 0.05;
            attribute :>> conversionEfficiency default = 0.9;
            attribute :>> uncertaintyFactor default = 1.15;
        }
        part telemetry :> loads {
            attribute :>> label = "Telemetry radio and command gateway";
            attribute :>> activePower default = 6 [W];
            attribute :>> idlePower default = 0.1 [W];
            attribute :>> activeFraction default = 0.02;
            attribute :>> conversionEfficiency default = 0.9;
            attribute :>> uncertaintyFactor default = 1.15;
        }
        part signaling :> loads {
            attribute :>> label = "Navigation signals";
            attribute :>> activePower default = 0.6 [W];
            attribute :>> idlePower default = 0 [W];
            attribute :>> activeFraction default = 0.5;
            attribute :>> conversionEfficiency default = 0.9;
            attribute :>> uncertaintyFactor default = 1.15;
        }
        part recording :> loads {
            attribute :>> label = "Recording electronics";
            attribute :>> activePower default = 0.2 [W];
            attribute :>> idlePower default = 0.05 [W];
            attribute :>> activeFraction default = 0.5;
            attribute :>> conversionEfficiency default = 0.9;
            attribute :>> uncertaintyFactor default = 1.15;
        }
        part health :> loads {
            attribute :>> label = "Recovery controller and ingress sensing";
            attribute :>> activePower default = 0.1 [W];
            attribute :>> idlePower default = 0.05 [W];
            attribute :>> activeFraction default = 1;
            attribute :>> conversionEfficiency default = 0.9;
            attribute :>> uncertaintyFactor default = 1.15;
        }
        part housekeeping :> loads {
            attribute :>> label = "Power management quiescent demand";
            attribute :>> activePower default = 0.2 [W];
            attribute :>> idlePower default = 0.2 [W];
            attribute :>> activeFraction default = 1;
            attribute :>> conversionEfficiency default = 0.9;
            attribute :>> uncertaintyFactor default = 1.15;
        }
        part payload :> loads {
            attribute :>> label = "Optional payload absent";
            attribute :>> activePower default = 0 [W];
            attribute :>> idlePower default = 0 [W];
            attribute :>> activeFraction default = 0;
            attribute :>> conversionEfficiency default = 0.9;
            attribute :>> uncertaintyFactor default = 1.15;
        }
    }
    part campaign : BlueDogEnergy::Scenario {
        part redefines battery {
            attribute :>> nominalEnergy default = 900000 [J];
            attribute :>> usableFraction default = 0.8;
            attribute :>> chargeEfficiency default = 0.9;
            attribute :>> dischargeEfficiency default = 0.9;
            attribute :>> selfDischargePower default = 0.02 [W];
            attribute :>> maxChargePower default = 30 [W];
            attribute :>> maxDischargePower default = 60 [W];
        }
        attribute :>> initialEnergy default = 648000 [J];
        attribute :>> recoveryMotorPower default = 50 [W];
        attribute :>> recoveryEssentialPower default = 8 [W];
        comment recoveryExample /* Synthetic route exposure for evaluator regression, not the challenge reserve policy. */
        attribute :>> recoveryPoweredDuration default = 1800 [s];
        attribute :>> recoveryEssentialDuration default = 7200 [s];
        attribute :>> recoveryUncertaintyFactor default = 1.2;
        ref part :>> timeline default = (dark1, harvest1, dark2, harvest2, dark3, harvest3);
        attribute :>> dayCount default = 3;
        attribute :>> evidenceAccepted default = false;
        part dark1 :> intervals {
            ref part :>> budget default = sailing;
            attribute :>> duration default = 64800 [s];
            attribute :>> harvestEnabled default = false;
            attribute :>> rawHarvestPower default = 0 [W];
            attribute :>> harvestEfficiency default = 0.85;
        }
        part harvest1 :> intervals {
            ref part :>> budget default = sailing;
            attribute :>> duration default = 21600 [s];
            attribute :>> harvestEnabled default = true;
            attribute :>> rawHarvestPower default = 40 [W];
            attribute :>> harvestEfficiency default = 0.85;
        }
        part dark2 :> intervals {
            ref part :>> budget default = sailing;
            attribute :>> duration default = 64800 [s];
            attribute :>> harvestEnabled default = false;
            attribute :>> rawHarvestPower default = 0 [W];
            attribute :>> harvestEfficiency default = 0.85;
        }
        part harvest2 :> intervals {
            ref part :>> budget default = sailing;
            attribute :>> duration default = 21600 [s];
            attribute :>> harvestEnabled default = true;
            attribute :>> rawHarvestPower default = 40 [W];
            attribute :>> harvestEfficiency default = 0.85;
        }
        part dark3 :> intervals {
            ref part :>> budget default = sailing;
            attribute :>> duration default = 64800 [s];
            attribute :>> harvestEnabled default = false;
            attribute :>> rawHarvestPower default = 0 [W];
            attribute :>> harvestEfficiency default = 0.85;
        }
        part harvest3 :> intervals {
            ref part :>> budget default = sailing;
            attribute :>> duration default = 21600 [s];
            attribute :>> harvestEnabled default = true;
            attribute :>> rawHarvestPower default = 40 [W];
            attribute :>> harvestEfficiency default = 0.85;
        }
    }
    dependency controllerAllocation from sailing::controller to BlueDog::Architecture::missionContext::boat::control;
    dependency navigationAllocation from sailing::navigation to BlueDog::Architecture::missionContext::boat::navigation;
    dependency trafficAllocation from sailing::traffic to BlueDog::Architecture::missionContext::boat::navigation::traffic;
    dependency sailAllocation from sailing::sail to BlueDog::Architecture::missionContext::boat::actuation;
    dependency steeringAllocation from sailing::steering to BlueDog::Architecture::missionContext::boat::actuation;
    dependency telemetryAllocation from sailing::telemetry to BlueDog::Architecture::missionContext::boat::communications;
    dependency signalingAllocation from sailing::signaling to BlueDog::Architecture::missionContext::boat::signaling;
    dependency recordingAllocation from sailing::recording to BlueDog::Architecture::missionContext::boat::recording;
    dependency healthAllocation from sailing::health to BlueDog::Architecture::missionContext::boat::recovery;
    dependency housekeepingAllocation from sailing::housekeeping to BlueDog::Architecture::missionContext::boat::energy::powerManagement;
    dependency payloadAllocation from sailing::payload to BlueDog::Architecture::missionContext::boat::observationPayload;
    dependency campaignIntent from campaign to BlueDogRequirements::multiDayEndurance;
}

package BlueDogIC01 {
    private import ScalarValues::*;
    doc /* IC-01 is the provisional finite-Gorge integration configuration.
     * The complete geometry is explicitly owned here. Exact values preserve the
     * 15 October archived candidate; they are not measured manufacturing precision.
     * The wing model is a sizing representation, not a rig selection. Soft sail,
     * tail-controlled wing and directly rotated fixed-camber wing remain contenders.
     * Physical qualification and accepted installed equipment remain open. */
    part design : MarineDesign::Design {
        attribute configurationId : String = "IC-01";
        attribute missionId : String = "Trans-Gorge";
        attribute designSource : String = "evidence/runs/2026-10-15-integrated-candidate/integrated-sizing.json";
        attribute sourceRevision : String = "86049ae5ee0429fd2c7b350228d3a544428a4aaf";
        attribute physicallyQualified : Boolean = false;
        attribute :>> length_m = 1.1999999999991275;
        attribute :>> beam_m = 0.42;
        attribute :>> bottom_depth_m = 0.1;
        attribute :>> deck_height_m = 0.07;
        attribute :>> sail_m2 = 0.4;
        attribute :>> sail_AR = 2.341980758978876;
        attribute :>> camber_scale = 1.5;
        attribute :>> wing_thickness_scale = 2.0;
        attribute :>> mast_fraction = 0.5238422485213118;
        attribute :>> mast_x_fraction = -0.1481170636448525;
        attribute :>> keel_m2 = 0.02;
        attribute :>> keel_span_m = 0.19999999999977908;
        attribute :>> rudder_m2 = 0.017679746777796716;
        attribute :>> rudder_span_m = 0.188041210379152;
        attribute :>> rudder_arm_fraction = 0.420003780182039;
        attribute :>> ballast_kg = 0.5;
        attribute :>> battery_Wh = 1300;
        attribute :>> panel_m2 = 0.05;
        attribute :>> wing_torque_Nm = 1.5;
        attribute :>> rudder_torque_Nm = 0.34378095116731916;
        attribute :>> hull_glass_kg_m2 = 0.452496128293465;
        attribute :>> wing_glass_kg_m2 = 0.4;
        attribute :>> keel_glass_kg_m2 = 2.5;
        attribute :>> rudder_glass_kg_m2 = 3;
        attribute :>> hull_rib_pitch_m = 0.022436816975681086;
        attribute :>> foil_rib_pitch_m = 0.2299999999996331;
        attribute :>> battery_x_fraction = -2.528793840994581e-11;
        attribute :>> battery_z_fraction = 0.05;
        attribute :>> hull_fullness_exponent = 2.0;
    }
    part integration {
        attribute identifier : String = design.configurationId;
        attribute additionalBusW : Real = 8;
        attribute additionalEquipmentKg : Real = 1.2;
        attribute independentRecoveryAssumed : Boolean = true;
        attribute recoveryBatteryWh : Real = 60;
        attribute recoveryStandbyW : Real = 0.05;
        attribute recoveryMotorW : Real = 50;
        attribute recoveryEssentialW : Real = 8;
        attribute recoverySpeedMps : Real = 1.5;
        attribute invertedSpeedMps : Real = 0.5;
        attribute invertedMotorW : Real = 40;
        attribute recoveryUncertainty : Real = 1.2;
        attribute arrivalAllowanceWh : Real = 2;
        attribute batteryWhKg : Real = BlueDogConfigurations::assumptions.batteryWhKg;
        attribute electronicsW : Real = BlueDogConfigurations::assumptions.electronicsW + additionalBusW;
        attribute fixedEquipmentKg : Real = BlueDogConfigurations::assumptions.fixedEquipmentKg + additionalEquipmentKg + recoveryBatteryWh/batteryWhKg;
        attribute recoveryDepartureWh : Real = recoveryBatteryWh*0.8*0.9;
        attribute sensorRangeM : Real = BlueDogEncounterReview::criteria.rangeAllocationM {
            doc /* Historical 15 October IC-01 sensing hypothesis retained for archived replay. The 750 m value is not a current class-specific allocation; BlueDogClassDetection allocations remain unaccepted.*/
        }
        attribute weedRangeM : Real = 40;
        attribute sensorLatencyS : Real = 1;
        attribute assessmentS : Real = 1;
        attribute commandS : Real = 2;
        attribute maneuverS : Real = 15;
        attribute planningHorizonS : Real = 180;
        attribute minimumSailingSpeedMps : Real = 0.05;
        attribute depowerPenaltyM : Real = 180;
        attribute crossTrackWeight : Real = 0.5;
        attribute maneuverPenaltyM : Real = 10;
    }
}

package BlueDogConfigurationManagement {
    private import ScalarValues::*;
    private import ISQ::*;
    private import SI::*;
    doc /* Configuration and resource-accounting context, tailored from NASA SE6.5/6.7,
     * defense SE Guidebook2026 6.1.3/6.1.6 and PSM/INCOSE Technical Measurement2005.
     * No numerical allocation, equipment selection or historical evidence changes. */
    part def ContextRecord {
        attribute identifier : String [1];
        attribute role : String [1];
        attribute intendedUse : String [1];
        attribute revisionBasis : String [1];
        ref part representedSubject [1];
    }
    part currentCandidate : ContextRecord {
        attribute :>> identifier = "IC-01";
        attribute :>> role = "Current numerical/integration candidate";
        attribute :>> intendedUse = "Conditional coupled sizing and local sailing/encounter/recovery studies; planned physical integration, not a built or qualified article";
        attribute :>> revisionBasis = "Current model source/model hashes identify a run. design.sourceRevision identifies the archived numerical origin, not the current hardware/software configuration revision.";
        ref part :>> representedSubject = BlueDogIC01::design;
    }
    part retainedSizing : ContextRecord {
        attribute :>> identifier = "Retained440Wh";
        attribute :>> role = "Historical sizing-study subject";
        attribute :>> intendedUse = "Interpret the retained candidate and its original archived replay; no transfer of its budget or evidence acceptance to IC-01";
        attribute :>> revisionBasis = "BlueDogSRRCurrent preserves the 440Wh record and original source revision; current reanalysis requires its own input fingerprints.";
        ref part :>> representedSubject = BlueDogSRRCurrent::candidate;
    }
    part illustrativeLoads : ContextRecord {
        attribute :>> identifier = "IllustrativeLoads";
        attribute :>> role = "Synthetic load-accounting example";
        attribute :>> intendedUse = "Demonstrate duty/conversion rollup; not a complete vessel or IC-01 installed-load split";
        attribute :>> revisionBasis = "BlueDogEnergyExamples source fingerprint identifies the illustrative allocation; it is not installed equipment evidence.";
        ref part :>> representedSubject = BlueDogEnergyExamples::sailing;
    }
    part searchReference : ContextRecord {
        attribute :>> identifier = "SearchReference";
        attribute :>> role = "Numerical starting geometry";
        attribute :>> intendedUse = "Reference geometry for preparation/search; not a selected vessel or accepted installed article";
        attribute :>> revisionBasis = "Current authored configuration fingerprint; original decimal precision is not measured accuracy.";
        ref part :>> representedSubject = BlueDogConfigurations::reference;
    }
    part lowerSearchBracket : ContextRecord {
        attribute :>> identifier = "LowerBracket";
        attribute :>> role = "Numerical/model-domain lower bracket";
        attribute :>> intendedUse = "Define search bounds; not a complete feasible vessel, owner requirement or manufacturing tolerance";
        attribute :>> revisionBasis = "Current model-domain/search input fingerprint; bracket changes need applicability and search review.";
        ref part :>> representedSubject = BlueDogConfigurations::lowerBracket;
    }
    part upperSearchBracket : ContextRecord {
        attribute :>> identifier = "UpperBracket";
        attribute :>> role = "Numerical/model-domain upper bracket";
        attribute :>> intendedUse = "Define search bounds; not a selected dimension, vessel requirement or manufacturing tolerance";
        attribute :>> revisionBasis = "Current model-domain/search input fingerprint; do not transfer bracket status to physical feasibility.";
        ref part :>> representedSubject = BlueDogConfigurations::upperBracket;
    }
    part parameterBasis : ContextRecord {
        attribute :>> identifier = "ParameterBasis";
        attribute :>> role = "Provisional shared analysis assumptions";
        attribute :>> intendedUse = "Reusable physical/component assumptions overridden by identified candidate integration inputs where declared";
        attribute :>> revisionBasis = "Current model/driver fingerprints identify assumptions; numerical allocations are not measured equipment.";
        ref part :>> representedSubject = BlueDogConfigurations::assumptions;
    }
    part recordedBaseline : ContextRecord {
        attribute :>> identifier = "RecordedBaseline";
        attribute :>> role = "Historical exploratory sizing projection";
        attribute :>> intendedUse = "Interpret the original October10 exploration; no silent substitution for current geometry or qualification";
        attribute :>> revisionBasis = "models/evidence/coupled-2026-10-10.sysml and evidence/runs/2026-10-10-coupled/manifest.json retain original revision.";
        ref part :>> representedSubject = BlueDogRecordedSizing::candidate;
    }
    part bingenProjection : ContextRecord {
        attribute :>> identifier = "BingenProjection";
        attribute :>> role = "Historical Bingen sizing projection";
        attribute :>> intendedUse = "Interpret the October12 Bingen candidate; distinct from the later 440Wh retained replay and IC-01";
        attribute :>> revisionBasis = "Despite the package name CurrentSizing, evidence/runs/2026-10-12-bingen/manifest.json owns this historical projection.";
        ref part :>> representedSubject = BlueDogCurrentSizing::candidate;
    }
    part continuationProjection : ContextRecord {
        attribute :>> identifier = "ContinuationProjection";
        attribute :>> role = "Historical coarse sizing continuation";
        attribute :>> intendedUse = "Interpret the recorded continuation subject; coarse feasibility and target status do not establish refinement or physical qualification";
        attribute :>> revisionBasis = "models/evidence/sizing-continuation.sysml preserves its recorded stage/result context; retain the archived run lineage.";
        ref part :>> representedSubject = BlueDogSizingContinuation::candidate;
    }
    part finitePassageProjection : ContextRecord {
        attribute :>> identifier = "FinitePassageProjection";
        attribute :>> role = "Historical finite-passage continuation";
        attribute :>> intendedUse = "Interpret the recorded partial/coarse progression and unreached target; no global infeasibility or current-vessel claim";
        attribute :>> revisionBasis = "evidence/runs/2026-10-12-finite-passage/manifest.json and native evidenceManifest retain the original scope/status.";
        ref part :>> representedSubject = BlueDogFinitePassageSizing::candidate;
    }
    part reliabilityIllustration : ContextRecord {
        attribute :>> identifier = "ReliabilityIllustration";
        attribute :>> role = "Synthetic exposure/rate example";
        attribute :>> intendedUse = "Exercise voyage-duration and constant-hazard arithmetic; not surveyed course geometry or collected vessel failure evidence";
        attribute :>> revisionBasis = "Current illustrative source fingerprint; profile/rates, dependence and statistical applicability remain unaccepted.";
        ref part :>> representedSubject = BlueDogReliabilityExamples::gorgeIllustration;
    }
    part def PlannedInstallation {
        ref part design : MarineDesign::Design [1];
        ref part assembly : BlueDogPhysicalArchitecture::IC01Candidate [1];
        attribute articleId : String [0..1];
        attribute hardwareRevision : String [0..1];
        attribute softwareDataRevision : String [0..1];
        attribute procedureRevision : String [0..1];
        attribute reconciliationRecord : String [0..1];
        attribute reconciled : Boolean default = false;
        attribute identityReady : Boolean = SequenceFunctions::size(articleId) == 1 and
        SequenceFunctions::size(hardwareRevision) == 1 and SequenceFunctions::size(softwareDataRevision) == 1 and
        SequenceFunctions::size(procedureRevision) == 1 and SequenceFunctions::size(reconciliationRecord) == 1 and
        articleId->ControlFunctions::forAll { in v : String; v != "" } and
        hardwareRevision->ControlFunctions::forAll { in v : String; v != "" } and
        softwareDataRevision->ControlFunctions::forAll { in v : String; v != "" } and
        procedureRevision->ControlFunctions::forAll { in v : String; v != "" } and
        reconciliationRecord->ControlFunctions::forAll { in v : String; v != "" };
        attribute plannedReferencesApplicable : Boolean = design == BlueDogIC01::design and assembly == BlueDogPhysicalArchitecture::ic01;
        attribute configurationReconciled : Boolean = plannedReferencesApplicable and identityReady and reconciled;
        doc /* A record identity does not inspect records or accept hardware. Include
         * applicable data/calibration in softwareDataRevision; a justified exclusion
         * belongs in the reconciliation record. No actual article is identified yet. */
    }
    part ic01Installation : PlannedInstallation {
        ref part :>> design = BlueDogIC01::design;
        ref part :>> assembly = BlueDogPhysicalArchitecture::ic01;
    }
    part def ResourceScope {
        attribute label : String [1];
        attribute quantityKind : String [1];
        ref part configuration : MarineDesign::Design [1] = BlueDogIC01::design;
        attribute boundary : String [1];
        attribute mode : String [1];
        attribute ownerRole : String [1];
        attribute basis : String [1];
        attribute closureEvidenceNeeded : String [1];
        attribute massAllocation : MassValue [0..1];
        attribute massEstimate : MassValue [0..1];
        attribute averagePowerAllocation : PowerValue [0..1];
        attribute peakPowerBound : PowerValue [0..1];
        attribute nameplateEnergy : EnergyValue [0..1];
        attribute departureEnergy : EnergyValue [0..1];
        attribute acquisitionLatency : TimeValue [0..1];
        attribute assessmentLatency : TimeValue [0..1];
        attribute commandLatency : TimeValue [0..1];
        attribute maneuverDuration : TimeValue [0..1];
        attribute coverageReviewed : Boolean default = false;
        attribute measurementsAccepted : Boolean default = false;
        attribute accountingReconciled : Boolean default = false;
        attribute evidenceRecord : String [0..1];
        attribute contextIdentified : Boolean = label != "" and quantityKind != "" and boundary != "" and
        mode != "" and ownerRole != "" and basis != "" and closureEvidenceNeeded != "";
        attribute quantitiesValid : Boolean =
            massAllocation->ControlFunctions::forAll { in v : MassValue; v >= 0 [kg] } and
        massEstimate->ControlFunctions::forAll { in v : MassValue; v >= 0 [kg] } and
        averagePowerAllocation->ControlFunctions::forAll { in v : PowerValue; v >= 0 [W] } and
        peakPowerBound->ControlFunctions::forAll { in v : PowerValue; v >= 0 [W] } and
        nameplateEnergy->ControlFunctions::forAll { in v : EnergyValue; v >= 0 [J] } and
        departureEnergy->ControlFunctions::forAll { in v : EnergyValue; v >= 0 [J] } and
        acquisitionLatency->ControlFunctions::forAll { in v : TimeValue; v >= 0 [s] } and
        assessmentLatency->ControlFunctions::forAll { in v : TimeValue; v >= 0 [s] } and
        commandLatency->ControlFunctions::forAll { in v : TimeValue; v >= 0 [s] } and
        maneuverDuration->ControlFunctions::forAll { in v : TimeValue; v >= 0 [s] };
        attribute requiredQuantitiesPresent : Boolean default = false;
        attribute ready : Boolean = contextIdentified and requiredQuantitiesPresent and quantitiesValid and coverageReviewed and measurementsAccepted and accountingReconciled and
        SequenceFunctions::size(evidenceRecord) == 1 and
        evidenceRecord->ControlFunctions::forAll { in v : String; v != "" };
        doc /* Allocations are bound to existing owners, not added measurements.
         * Empty quantities are unknown/not supplied or outside the row's scope.
         * Review the boundary and quantityKind before interpreting or aggregating.
         * No total, headroom or zero entry is fabricated for missing information. */
    }
    part def AccountingCase {
        ref part installation : PlannedInstallation [1];
        part scopes : ResourceScope [1..*];
    }
    part ic01 : AccountingCase {
        ref part :>> installation = ic01Installation;
        part wholeVesselMass : ResourceScope subsets scopes {
            attribute :>> requiredQuantitiesPresent = SequenceFunctions::size(massEstimate) == 1;
            attribute :>> label = "Whole-vessel mass estimate, not supplied in this register";
            attribute :>> quantityKind = "Total vessel mass estimate; distinct from component allowances";
            attribute :>> boundary = "Complete loaded vessel: structure, rig, appendages, batteries, equipment, attachment and support/finish contributions. Fixed equipment is one contribution; do not add it again after a complete native mass rollup.";
            attribute :>> mode = "Same loaded IC-01 geometry, equipment and carried-fluid configuration as the associated performance/handling/recovery study";
            attribute :>> ownerRole = "System integration/mass";
            attribute :>> basis = "A new identified coupled/native MassProperties execution is needed to populate this register. Historical IC-01 or reference-design estimates keep their own recorded source/configuration; none is silently substituted here.";
            attribute :>> closureEvidenceNeeded = "Current coupled/native mass/CG result with exact source/geometry inputs, complete installation reconciliation and weighed-article evidence for physical claims; compare with the applicable handling criterion";
        }
        part mainStorage : ResourceScope subsets scopes {
            attribute :>> requiredQuantitiesPresent = SequenceFunctions::size(nameplateEnergy) == 1 and SequenceFunctions::size(departureEnergy) == 1;
            attribute :>> label = "Main sailing storage account";
            attribute :>> quantityKind = "Nameplate and allocated departure stored energy; successive states";
            attribute :>> boundary = "One main bank; nameplate, usable and departure states are not additive. Sailing withdrawal/losses/self-discharge and its protected reserve belong to the same finite-passage screen. Independent recovery storage is separate; no cross-bank transfer is credited.";
            attribute :>> mode = "Finite-Gorge passage/holds with current sizing usable/departure fractions; no solar credit in the IC-01 integration hypothesis";
            attribute :>> ownerRole = "Power/energy integration";
            attribute :>> basis = "BlueDogIC01.design.battery_Wh and BlueDogOperatingEnvironment.Inputs usable_fraction/initial_fraction; existing allocations, not measured storage capability";
            attribute :>> nameplateEnergy = BlueDogIC01::design.battery_Wh * 3600 [J];
            attribute :>> departureEnergy = nameplateEnergy * BlueDogOperatingEnvironment::Inputs.usable_fraction * BlueDogOperatingEnvironment::Inputs.initial_fraction;
            attribute :>> closureEvidenceNeeded = "Installed bank usable capacity, initial energy and temperature/end-of-service basis; complete withdrawal/reserve history and measured voltage/current/peak capability, coupled passage and casualty assessment";
        }
        part fixedEquipment : ResourceScope subsets scopes {
            attribute :>> requiredQuantitiesPresent = SequenceFunctions::size(massAllocation) == 1;
            attribute :>> label = "Fixed-equipment mass allowance";
            attribute :>> quantityKind = "Mass allocation, not total vessel mass";
            attribute :>> boundary = "Base fixed equipment plus additional equipment plus recovery battery mass. Wind installation, geometry/materials, main battery and actuator models are accounted separately; do not add the recovery battery again.";
            attribute :>> mode = "Candidate installed mass/CG accounting across sailing and recovery";
            attribute :>> ownerRole = "System integration/mass";
            attribute :>> basis = "BlueDogIC01.integration.fixedEquipmentKg; specific-energy conversion is an allowance, not weighed hardware";
            attribute :>> massAllocation = BlueDogIC01::integration.fixedEquipmentKg * 1 [kg];
            attribute :>> closureEvidenceNeeded = "Complete non-overlapping BOM, installation/support mass and locations; weighed articles, packaging and coupled mass/CG/performance reconciliation";
        }
        part sailingElectronics : ResourceScope subsets scopes {
            attribute :>> requiredQuantitiesPresent = SequenceFunctions::size(averagePowerAllocation) == 1 and SequenceFunctions::size(peakPowerBound) == 1;
            attribute :>> label = "Sailing electronics bus allowance";
            attribute :>> quantityKind = "Average bus power allocation; peak unknown";
            attribute :>> boundary = "Base electronics including separately provisioned wired wind plus additionalBusW. The additional 8W is inside this row, not another additive load; actuator demand is separate.";
            attribute :>> mode = "Qualifying sailing/holds under the declared performance and duty assumptions";
            attribute :>> ownerRole = "Power/sensing integration";
            attribute :>> basis = "BlueDogIC01.integration.electronicsW; no installed component split or startup/stall/coincident peak bound";
            attribute :>> averagePowerAllocation = BlueDogIC01::integration.electronicsW * 1 [W];
            attribute :>> closureEvidenceNeeded = "Selected acquisition/processing/navigation/recording/communications/signaling/support loads, explicit replacements, measured duty/thermal/peak performance and supplied bus compatibility";
        }
        part recoveryEssentials : ResourceScope subsets scopes {
            attribute :>> requiredQuantitiesPresent = SequenceFunctions::size(averagePowerAllocation) == 1 and SequenceFunctions::size(peakPowerBound) == 1;
            attribute :>> label = "Recovery essential-load allowance";
            attribute :>> quantityKind = "Active recovery withdrawal-power allocation; peak unknown";
            attribute :>> boundary = "8W essentials used by the recovery demand model, separately from active motor and voyage standby. Not a measured bus split; record-storage and telemetry supply assignment is unresolved.";
            attribute :>> mode = "Active upright/inverted recovery after loss of primary sailing";
            attribute :>> ownerRole = "Recovery/power";
            attribute :>> basis = "BlueDogIC01.integration.recoveryEssentialW; preserve the recovery model's battery-withdrawal boundary and do not apply bus conversion twice";
            attribute :>> averagePowerAllocation = BlueDogIC01::integration.recoveryEssentialW * 1 [W];
            attribute :>> closureEvidenceNeeded = "Installed surviving functions, actual supply topology, conversions, simultaneous load and fault isolation; measured casualty performance";
        }
        part recoveryStorage : ResourceScope subsets scopes {
            attribute :>> requiredQuantitiesPresent = SequenceFunctions::size(nameplateEnergy) == 1 and SequenceFunctions::size(departureEnergy) == 1;
            attribute :>> label = "Independent recovery storage account";
            attribute :>> quantityKind = "Nameplate and departure stored energy; successive states";
            attribute :>> boundary = "Nameplate and departure are not additive capacity. Standby depletes departure energy; route/casualty demand is assessed against the remaining bank. Main-pack protected reserve remains a separate conservative screen, with no pack transfer credited.";
            attribute :>> mode = "Voyage standby then route-dependent casualty recovery";
            attribute :>> ownerRole = "Recovery/energy";
            attribute :>> basis = "BlueDogIC01.integration.recoveryBatteryWh/recoveryDepartureWh; 1Wh=3600J";
            attribute :>> nameplateEnergy = BlueDogIC01::integration.recoveryBatteryWh * 3600 [J];
            attribute :>> departureEnergy = BlueDogIC01::integration.recoveryDepartureWh * 3600 [J];
            attribute :>> closureEvidenceNeeded = "Same installed bank's temperature/end-of-service usable capacity, initial energy, standby history and casualty route demand, peaks and no-transfer/isolation evidence";
        }
        part responseTiming : ResourceScope subsets scopes {
            attribute :>> requiredQuantitiesPresent = SequenceFunctions::size(acquisitionLatency) == 1 and SequenceFunctions::size(assessmentLatency) == 1 and SequenceFunctions::size(commandLatency) == 1 and SequenceFunctions::size(maneuverDuration) == 1;
            attribute :>> label = "Allocated encounter response stages";
            attribute :>> quantityKind = "Individual time allowances, not an accepted end-to-end bound";
            attribute :>> boundary = "Acquisition/assessment/command/maneuver allowances belong to separate response stages. Queueing, overlap, clock uncertainty and occupied-actuator delay need a whole-path model; do not infer a complete deadline by adding labels.";
            attribute :>> mode = "Local IC-01 encounter hypothesis, including degraded/occupied response";
            attribute :>> ownerRole = "Control/sensing integration";
            attribute :>> basis = "BlueDogIC01.integration.sensorLatencyS/assessmentS/commandS/maneuverS";
            attribute :>> acquisitionLatency = BlueDogIC01::integration.sensorLatencyS * 1 [s];
            attribute :>> assessmentLatency = BlueDogIC01::integration.assessmentS * 1 [s];
            attribute :>> commandLatency = BlueDogIC01::integration.commandS * 1 [s];
            attribute :>> maneuverDuration = BlueDogIC01::integration.maneuverS * 1 [s];
            attribute :>> closureEvidenceNeeded = "Synchronized installed observations, scheduling, delivered command and achieved motion, interacting faults and current class/clearance acceptance criteria";
        }
    }
    analysis def AccountingReview {
        subject account : AccountingCase;
        out attribute scopeCount : Integer = SequenceFunctions::size(account.scopes);
        out attribute allScopesSameConfiguration : Boolean = account.scopes->ControlFunctions::forAll {
            in row : ResourceScope; row.configuration == account.installation.design };
        out attribute installationReconciled : Boolean = account.installation.configurationReconciled;
        out attribute resourceEvidenceReady : Boolean = scopeCount > 0 and account.scopes->ControlFunctions::forAll {
            in row : ResourceScope; row.ready };
        return ready : Boolean = allScopesSameConfiguration and installationReconciled and resourceEvidenceReady;
    }
    analysis currentReview : AccountingReview { subject = ic01; }
    dependency wholeMassBasis from ic01::wholeVesselMass to BlueDogCoupledSizing::MassProperties;
    dependency mainStorageBasis from ic01::mainStorage to BlueDogIC01::design::battery_Wh;
    dependency massBasis from ic01::fixedEquipment to BlueDogIC01::integration::fixedEquipmentKg;
    dependency sailingBasis from ic01::sailingElectronics to BlueDogIC01::integration::electronicsW;
    dependency recoveryLoadBasis from ic01::recoveryEssentials to BlueDogIC01::integration::recoveryEssentialW;
    dependency storageBasis from ic01::recoveryStorage to BlueDogIntegratedCandidate::RecoveryScreen;
    dependency timingBasis from ic01::responseTiming to BlueDogEncounterReview::criteria;
    metadata issue : ModelingMetadata::Issue { text = "C-01: Identify installed article/hardware/software-data/procedure revisions and reconcile actual configuration. C-02: Replace lumped allowances with non-overlapping measured installation accounting, including signal/record/telemetry and recovery supplies. C-03: Reconcile modes, peaks, storage/conversion/reserve boundaries and mass/CG/performance coupling. C-04: Establish uncertainty/margin and change/retest triggers from evidence; none of these accounting scopes is accepted physical evidence."; }
}

package BlueDogOperatingEnvironment {
    private import ScalarValues::*;
    private import SI::*;
    analysis Inputs {
        doc /* Provisional operating and energy allocations. Physical values remain separate from numerical optimizer tolerances. */
        out attribute foil_alpha_limit_deg : Real = 12;
        out attribute rudder_inflow_ratio : Real = 0.8;
        out attribute hinge_fraction : Real = RealFunctions::abs(BlueDogConceptCredibility::policy.rudderStockChordFraction-BlueDogConceptCredibility::policy.rudderLoadChordFraction);
        out attribute friction_Nm : Real = 0.02;
        out attribute max_froude : Real = 0.65;
        out attribute min_wing_Re : Real = 60000;
        out attribute min_foil_Re : Real = 30000;
        out attribute yaw_reserve_Nm : Real = 0.5;
        out attribute control_speed_m_s : Real = 0.5;
        out attribute control_wind_m_s : Real = 5;
        out attribute peak_irradiance_W_m2 : Real = 1000;
        out attribute panel_efficiency : Real = 0.2;
        out attribute harvest_efficiency : Real = 0.85;
        out attribute charge_efficiency : Real = 0.9;
        out attribute discharge_efficiency : Real = 0.9;
        out attribute usable_fraction : Real = 0.8;
        out attribute initial_fraction : Real = 0.9;
        out attribute charge_C_rate : Real = 0.5;
        out attribute discharge_C_rate : Real = 1.5;
        out attribute self_discharge_W : Real = 0.02;
        out attribute dark_hours : Real = 18;
        out attribute solar_hours : Real = 6;
        comment reserveScreen /* Synthetic comparison exposure only; mission feasibility requires the course-dependent reserve provider. */
        out attribute reserve_Wh : Real = BlueDogRequirements::RecoveryReserveDemand(50 [W], 8 [W], 1800 [s], 7200 [s], 1.2) / (3600 [J]);
        out attribute wingMomentScale : Real = BlueDogAerodynamicPolicy::sizing.momentScale;
        out attribute parameterNames : String [*] ordered nonunique = ("foil_alpha_limit_deg", "rudder_inflow_ratio", "hinge_fraction", "friction_Nm", "max_froude", "min_wing_Re", "min_foil_Re", "yaw_reserve_Nm", "control_speed_m_s", "control_wind_m_s", "peak_irradiance_W_m2", "panel_efficiency", "harvest_efficiency", "charge_efficiency", "discharge_efficiency", "usable_fraction", "initial_fraction", "charge_C_rate", "discharge_C_rate", "self_discharge_W", "dark_hours", "solar_hours", "reserve_Wh", "wingMomentScale");
        out attribute parameterValues : Real [*] ordered nonunique = (foil_alpha_limit_deg, rudder_inflow_ratio, hinge_fraction, friction_Nm, max_froude, min_wing_Re, min_foil_Re, yaw_reserve_Nm, control_speed_m_s, control_wind_m_s, peak_irradiance_W_m2, panel_efficiency, harvest_efficiency, charge_efficiency, discharge_efficiency, usable_fraction, initial_fraction, charge_C_rate, discharge_C_rate, self_discharge_W, dark_hours, solar_hours, reserve_Wh, wingMomentScale);
    }
}

package BlueDogSailingExamples {
    private import SI::*;
    doc /* Synthetic design studies. No measured hull, polar or route is asserted.
     * Wind from west/east denotes idealized alignment with a straight river axis,
     * not a weather forecast or surveyed corridor. Length is waterline length of
     * the assembled vessel, not a printer-module dimension. gorgeWesterly is
     * the representative selected-window challenge illustration; gorgeEasterly
     * is a reversal/winter sensitivity. Neither is a probability-weighted route.
     * BlueDogWeather::policy governs seasonal context, not these synthetic speeds.
     */
    part def UpstreamHeadwind :> BlueDogSailing::PolarLeg {
        attribute :>> label default = "Upstream / headwind";
        attribute :>> distance default = 100000 [m];
        attribute :>> currentVMG default = -1.5 [m/s];
        attribute :>> retainedPerformance default = 0.8;
        attribute :>> trueWindSpeed default = 5 [m/s];
        attribute :>> trueWindAngle default = TrigFunctions::rad(45) * (1 [rad]);
        attribute :>> leeway default = 0 [rad];
        attribute :>> windward default = true;
        attribute :>> cleanPolarSpeed default = 4 [m/s];
        attribute :>> maneuverRetention default = 0.95;
        attribute :>> waterlineLength default = 1 [m];
        attribute :>> allocatedTime default = 201600 [s];
        attribute :>> minimumGroundVMG default = 0.5 [m/s];
        attribute :>> polarEvidenceAccepted default = false;
        attribute :>> hullEvidenceAccepted default = false;
    }
    part def UpstreamTailwind :> UpstreamHeadwind {
        attribute :>> label default = "Upstream / tailwind";
        attribute :>> trueWindAngle default = TrigFunctions::rad(140) * (1 [rad]);
        attribute :>> windward default = false;
        attribute :>> cleanPolarSpeed default = 3.6 [m/s];
    }
    part def DownstreamHeadwind :> UpstreamHeadwind {
        attribute :>> label default = "Downstream / headwind";
        attribute :>> currentVMG default = 1.5 [m/s];
        attribute :>> allocatedTime default = 36000 [s];
        attribute :>> cleanPolarSpeed default = 3 [m/s];
    }
    part def DownstreamTailwind :> DownstreamHeadwind {
        attribute :>> label default = "Downstream / tailwind";
        attribute :>> trueWindAngle default = TrigFunctions::rad(140) * (1 [rad]);
        attribute :>> windward default = false;
    }
    part upstreamHeadwind : UpstreamHeadwind;
    part upstreamTailwind : UpstreamTailwind;
    part downstreamHeadwind : DownstreamHeadwind;
    part downstreamTailwind : DownstreamTailwind;
    part gorgeWesterly : BlueDogSailing::PolarVoyageProfile {
        ref part :>> vessel = BlueDog::Architecture::missionContext.boat;
        part upstream : UpstreamTailwind subsets legs;
        part downstream : DownstreamHeadwind subsets legs;
        attribute :>> holdTime default = BlueDogReliabilityExamples::gorgeIllustration.holdTime;
        attribute :>> qualifiedDuration default = BlueDogReliabilityExamples::gorgeIllustration.qualifiedDuration;
        attribute :>> criticalRatesPerHour default = BlueDogReliabilityExamples::gorgeIllustration.criticalRatesPerHour;
        attribute :>> commonCauseRatePerHour default = BlueDogReliabilityExamples::gorgeIllustration.commonCauseRatePerHour;
        attribute :>> zeroFailureTestHours default = BlueDogReliabilityExamples::gorgeIllustration.zeroFailureTestHours;
        attribute :>> observedCriticalFailures default = BlueDogReliabilityExamples::gorgeIllustration.observedCriticalFailures;
        attribute :>> rateEvidenceAccepted default = false;
        attribute :>> constantHazardAccepted default = false;
    }
    part gorgeEasterly :> gorgeWesterly {
        part redefines upstream {
            attribute :>> label = upstreamHeadwind.label;
            attribute :>> trueWindAngle = upstreamHeadwind.trueWindAngle;
            attribute :>> windward = true;
            attribute :>> cleanPolarSpeed = upstreamHeadwind.cleanPolarSpeed;
        }
        part redefines downstream {
            attribute :>> label = downstreamTailwind.label;
            attribute :>> trueWindAngle = downstreamTailwind.trueWindAngle;
            attribute :>> windward = false;
            attribute :>> cleanPolarSpeed = downstreamTailwind.cleanPolarSpeed;
        }
    }
    analysis upstreamBeat : BlueDogSailing::PolarDemandAndHullScreen { subject :>> leg = upstreamHeadwind; }
    analysis upstreamRun : BlueDogSailing::PolarDemandAndHullScreen { subject :>> leg = upstreamTailwind; }
    analysis downstreamBeat : BlueDogSailing::PolarDemandAndHullScreen { subject :>> leg = downstreamHeadwind; }
    analysis downstreamRun : BlueDogSailing::PolarDemandAndHullScreen { subject :>> leg = downstreamTailwind; }
    analysis westerlyPassage : BlueDogSailing::PolarVoyageAssessment { subject :>> profile = gorgeWesterly; }
    analysis easterlyPassage : BlueDogSailing::PolarVoyageAssessment { subject :>> profile = gorgeEasterly; }
    part lightWind : UpstreamHeadwind { attribute :>> trueWindSpeed = 3 [m/s]; }
    part strongWind : UpstreamHeadwind { attribute :>> trueWindSpeed = 10 [m/s]; }
    part highWind : UpstreamHeadwind { attribute :>> trueWindSpeed = 15 [m/s]; }
    analysis lightWindDemand : BlueDogSailing::PolarDemandAndHullScreen { subject :>> leg = lightWind; }
    analysis strongWindDemand : BlueDogSailing::PolarDemandAndHullScreen { subject :>> leg = strongWind; }
    analysis highWindDemand : BlueDogSailing::PolarDemandAndHullScreen { subject :>> leg = highWind; }
    analysis sensitivity : BlueDogSailing::SailingSensitivity { subject :>> leg = upstreamHeadwind; }
    part oceanIllustration : UpstreamHeadwind {
        doc /* Sizing probe only: 4000 km in 28 moving days (30 days less 48 h holds),
         * zero along-route current, 140-degree TWA. No Hawaii route, season, wind
         * persistence, endurance qualification or operating window is established. */
        metadata issue : ModelingMetadata::Issue { text = "Illustrative distance and time allocation are not approved Hawaii mission parameters."; }
        attribute :>> label = "Offshore sizing probe";
        attribute :>> distance = 4000000 [m];
        attribute :>> currentVMG = 0 [m/s];
        attribute :>> allocatedTime = 2419200 [s];
        attribute :>> trueWindAngle = TrigFunctions::rad(140) * (1 [rad]);
        attribute :>> windward = false;
        attribute :>> cleanPolarSpeed = 3 [m/s];
    }
    analysis oceanDemand : BlueDogSailing::PolarDemandAndHullScreen { subject :>> leg = oceanIllustration; }
    dependency oceanSizingBasis from oceanIllustration to BlueDog::Goals::hawaiiVoyage;
}

package BlueDogConfigurations {
    private import ScalarValues::*;
    part reference : MarineDesign::Design {
        metadata rationale : ModelingMetadata::Rationale { text = "Starting geometry only; all represented dimensions remain free in sizing."; }
        attribute :>> length_m = 2;
        attribute :>> beam_m = 0.60443680369999997;
        attribute :>> bottom_depth_m = 0.052643588900000003;
        attribute :>> deck_height_m = 0.16320739109999999;
        attribute :>> sail_m2 = 1.1782673035;
        attribute :>> sail_AR = 5.2091181580999999;
        attribute :>> camber_scale = 1;
        attribute :>> wing_thickness_scale = 1;
        attribute :>> mast_fraction = 0.5;
        attribute :>> mast_x_fraction = -0.017302668;
        attribute :>> keel_m2 = 0.14177613859999999;
        attribute :>> keel_span_m = 0.71481970699999997;
        attribute :>> rudder_m2 = 0.0120845842;
        attribute :>> rudder_span_m = 0.12816840779999999;
        attribute :>> rudder_arm_fraction = 0.5;
        attribute :>> ballast_kg = 11.6735943;
        attribute :>> battery_Wh = 207.46827300000001;
        attribute :>> panel_m2 = 0.23102358200000001;
        attribute :>> wing_torque_Nm = 0.80857334999999997;
        attribute :>> rudder_torque_Nm = 0.80857334999999997;
        attribute :>> hull_glass_kg_m2 = 0.59999999999999998;
        attribute :>> wing_glass_kg_m2 = 0.40000000000000002;
        attribute :>> keel_glass_kg_m2 = 4.7999999999999998;
        attribute :>> rudder_glass_kg_m2 = 0.40000000000000002;
        attribute :>> hull_rib_pitch_m = 0.029750749999999999;
        attribute :>> foil_rib_pitch_m = 0.040000000000000001;
        attribute :>> battery_x_fraction = 0;
        attribute :>> battery_z_fraction = 0.10000000000000001;
        attribute :>> hull_fullness_exponent = 1.8;
    }
    part assumptions : MarineDesign::Parameters {
        metadata rationale : ModelingMetadata::Rationale { text = "Provisional physical and component allocations; uncertainty cases and evidence limitations remain separate from a numerical pass."; }
        attribute :>> resinGlassRatio = 1;
        attribute :>> gearboxEfficiency = 0.40000000000000002;
        attribute :>> motorEfficiency = 0.80000000000000004;
        attribute :>> wingNoLoadW = 1;
        attribute :>> wingControllerW = 0.10000000000000001;
        attribute :>> wingMotorHoldingW = 0;
        attribute :>> wingMoveFraction = 0.02;
        attribute :>> wingHoldingFraction = 0.97999999999999998;
        attribute :>> rudderHoldingWPerNm = 0.5;
        attribute :>> rudderMoveFraction = 0.050000000000000003;
        attribute :>> electronicsW = 4.5 + BlueDogWindEquipment::challenge.busPowerW;
        attribute :>> solarResourceFactor = 0.59999999999999998;
        attribute :>> batteryWhKg = 140;
        attribute :>> laminateKnockdown = 1;
        attribute :>> profileCd = BlueDogAerodynamicPolicy::sizing.profileCd;
        attribute :>> wingClLimit = BlueDogAerodynamicPolicy::sizing.clLimit;
        attribute :>> wingLiftScale = BlueDogAerodynamicPolicy::sizing.liftScale;
        attribute :>> wingDragScale = BlueDogAerodynamicPolicy::sizing.dragScale;
        attribute :>> wingRateRadS = 0.25;
        attribute :>> rudderRateRadS = 0.59999999999999998;
        attribute :>> driveKgPerNm = 0.14999999999999999;
        attribute :>> wingDriveBaseKg = 0.20000000000000001;
        // Base equipment excludes the separately located wind-sensing installation.
        attribute :>> fixedEquipmentKg = 2.5;
        attribute :>> elevatedEquipmentKg = BlueDogWindEquipment::challenge.installedMassKg;
        attribute :>> elevatedEquipmentXFraction = BlueDogWindEquipment::challenge.xFraction;
        attribute :>> elevatedEquipmentAboveDeckM = BlueDogWindEquipment::challenge.aboveDeckM;
        attribute :>> attachmentKg = 0.59999999999999998;
        attribute :>> residuaryResistanceFactor = 1;
        attribute :>> viscousFormFactor = 1.1499999999999999;
        attribute :>> foilClLimit = 0.80000000000000004;
        attribute :>> foilEfficiency = 0.69999999999999996;
        attribute :>> foilCd = 0.012;
        attribute :>> airNu = 1.5e-05;
        attribute :>> waterNu = 9.9999999999999995e-07;
        attribute :>> waterDensity = 1000;
        attribute :>> airDensity = 1.2250000000000001;
        attribute :>> ballastDensity = 7800;
        attribute :>> gravity = 9.8066499999999994;
        attribute :>> loadFactor = 1.5;
        attribute :>> assemblyLimitKg = 15;
        attribute :>> panelCoverage = 0.59999999999999998;
    }
    part lowerBracket : MarineDesign::Design {
        doc /* Numerical and physical-model domain bracket, not a vessel requirement or selected dimension. */
        attribute :>> length_m = 0.8;
        attribute :>> beam_m = 0.2;
        attribute :>> bottom_depth_m = 0.02;
        attribute :>> deck_height_m = 0.05;
        attribute :>> sail_m2 = 0.2;
        attribute :>> sail_AR = 2;
        attribute :>> camber_scale = 0.5;
        attribute :>> wing_thickness_scale = 0.5;
        attribute :>> mast_fraction = 0.1;
        attribute :>> mast_x_fraction = -0.4;
        attribute :>> keel_m2 = 0.02;
        attribute :>> keel_span_m = 0.15;
        attribute :>> rudder_m2 = 0.005;
        attribute :>> rudder_span_m = 0.08;
        attribute :>> rudder_arm_fraction = 0.25;
        attribute :>> ballast_kg = 0.5;
        attribute :>> battery_Wh = 50;
        attribute :>> panel_m2 = 0.05;
        attribute :>> wing_torque_Nm = 0.05;
        attribute :>> rudder_torque_Nm = 0.05;
        attribute :>> hull_glass_kg_m2 = 0.2;
        attribute :>> wing_glass_kg_m2 = 0.2;
        attribute :>> keel_glass_kg_m2 = 0.2;
        attribute :>> rudder_glass_kg_m2 = 0.2;
        attribute :>> hull_rib_pitch_m = 0.01;
        attribute :>> foil_rib_pitch_m = 0.01;
        attribute :>> battery_x_fraction = -0.35;
        attribute :>> battery_z_fraction = 0.05;
        attribute :>> hull_fullness_exponent = 1.0;
    }
    part upperBracket : MarineDesign::Design {
        doc /* Numerical and physical-model domain bracket, not a vessel requirement or selected dimension. */
        attribute :>> length_m = 4;
        attribute :>> beam_m = 1.2;
        attribute :>> bottom_depth_m = 0.3;
        attribute :>> deck_height_m = 0.5;
        attribute :>> sail_m2 = 4;
        attribute :>> sail_AR = 8;
        attribute :>> camber_scale = 1.5;
        attribute :>> wing_thickness_scale = 2;
        attribute :>> mast_fraction = 0.9;
        attribute :>> mast_x_fraction = 0.4;
        attribute :>> keel_m2 = 0.5;
        attribute :>> keel_span_m = 1.1;
        attribute :>> rudder_m2 = 0.2;
        attribute :>> rudder_span_m = 0.6;
        attribute :>> rudder_arm_fraction = 0.65;
        attribute :>> ballast_kg = 14.5;
        attribute :>> battery_Wh = 1000;
        attribute :>> panel_m2 = 1;
        attribute :>> wing_torque_Nm = 20;
        attribute :>> rudder_torque_Nm = 10;
        attribute :>> hull_glass_kg_m2 = 4;
        attribute :>> wing_glass_kg_m2 = 4;
        attribute :>> keel_glass_kg_m2 = 8;
        attribute :>> rudder_glass_kg_m2 = 4;
        attribute :>> hull_rib_pitch_m = 0.23;
        attribute :>> foil_rib_pitch_m = 0.23;
        attribute :>> battery_x_fraction = 0.35;
        attribute :>> battery_z_fraction = 0.9;
        attribute :>> hull_fullness_exponent = 2.0;
    }
}

package BlueDogReliabilityExamples {
    private import SI::*;
    part gorgeIllustration : BlueDogReliability::VoyageProfile {
        doc /* Synthetic 100 km each-way profile; not surveyed challenge gates or a predicted polar.
         * 2.5 m/s water VMG with 20 percent loss, +/-1.5 m/s current, six hours of holds.
         * Failure-rate and test-hour inputs are illustrative, not collected evidence. */
        ref part :>> vessel = BlueDog::Architecture::missionContext.boat;
        part upstream : BlueDogReliability::SailingLeg subsets legs {
            attribute :>> distance default = 100000 [m];
            attribute :>> waterVMG default = 2.5 [m/s];
            attribute :>> currentVMG default = -1.5 [m/s];
            attribute :>> retainedPerformance default = 0.8;
        }
        part downstream : BlueDogReliability::SailingLeg subsets legs {
            attribute :>> distance default = 100000 [m];
            attribute :>> waterVMG default = 2.5 [m/s];
            attribute :>> currentVMG default = 1.5 [m/s];
            attribute :>> retainedPerformance default = 0.8;
        }
        attribute :>> holdTime default = 21600 [s];
        attribute :>> qualifiedDuration default = 259200 [s];
        attribute :>> criticalRatesPerHour default = (0.0002, 0.0003);
        attribute :>> commonCauseRatePerHour default = 0.0001;
        attribute :>> zeroFailureTestHours default = 2000;
        attribute :>> observedCriticalFailures default = 0;
        attribute :>> profileEvidenceAccepted default = false;
        attribute :>> rateEvidenceAccepted default = false;
        attribute :>> constantHazardAccepted default = false;
    }
    analysis gorgeAssessment : BlueDogReliability::CruiseReliability { subject :>> profile = gorgeIllustration; }
}

package BlueDogSensingEquipment {
    doc /* Physical installation hypotheses reviewed 2026-10-16. Supplier specifications are component inputs, not demonstrated detection range, latency or full installed budgets. See evidence/sensing/2026-10-16/sources.json and docs/reference/sensing-configurations.md. No sensing simulation is changed by this package.*/
    private import ScalarValues::*;
    part fixedHighResolution {
        doc /* SC-01: four Luxonis OAK-1 W IMX378 fixed-focus cameras at 90 degree azimuth spacing; on-camera RVC2 inference; Raspberry Pi4 ModelB host; externally powered USB3 hub; Quark QK-A026 AIS/GPS and separate antennas. Four95deg horizontal fields give only5deg nominal adjacent overlap before occlusion or calibration.*/
        attribute id : String = "SC-01";
        attribute cameraCount : Real = 4;
        attribute horizontalPixels : Real = 4056;
        attribute horizontalFovDeg : Real = 95;
        attribute cameraMassKg : Real = 0.0531;
        attribute cameraStreamingLowW : Real = 2.5;
        attribute cameraStreamingHighW : Real = 3.0;
        attribute cameraAiAllowanceW : Real = 1.0;
        attribute cameraEncoderAllowanceW : Real = 0.5;
        attribute knownCameraMassKg : Real = 0.2124;
        attribute nominalOverlapDeg : Real = 5;
        attribute primaryPlanningMassKg : Real = 0.9824;
        attribute cameraStreamingSubtotalLowW : Real = 10.0;
        attribute cameraFeatureAllowanceHighW : Real = 18.0;
        attribute installedBudgetComplete : Boolean = false;
        attribute rangeDemonstrated : Boolean = false;
        attribute latencyDemonstrated : Boolean = false;
        attribute invertedObservationDemonstrated : Boolean = false;
        attribute independentRecoveryComplete : Boolean = false;
        attribute recoveryBlocker : String = "Separate recovery power alone is insufficient: independent host, observation geometry, navigation, antennas and sealed upright/inverted mounting remain unselected. No primary camera/hub credit after shared failure or immersion.";
    }
    part fixedGlobalShutter {
        doc /* SC-02: three Luxonis OAK-1 W OV9782 fixed-focus global-shutter cameras at120degree spacing; same Pi4B host, powered hub andQKA026 AIS/GPS. Three127degree fields give7degree nominal adjacent overlap. Lower resolution trades angular detail for fewer camera loads.*/
        attribute id : String = "SC-02";
        attribute cameraCount : Real = 3;
        attribute horizontalPixels : Real = 1280;
        attribute horizontalFovDeg : Real = 127;
        attribute cameraMassKg : Real = 0.0531;
        attribute cameraStreamingLowW : Real = 2.5;
        attribute cameraStreamingHighW : Real = 3.0;
        attribute cameraAiAllowanceW : Real = 1.0;
        attribute cameraEncoderAllowanceW : Real = 0.5;
        attribute knownCameraMassKg : Real = 0.1593;
        attribute nominalOverlapDeg : Real = 7;
        attribute primaryPlanningMassKg : Real = 0.8493;
        attribute cameraStreamingSubtotalLowW : Real = 7.5;
        attribute cameraFeatureAllowanceHighW : Real = 13.5;
        attribute installedBudgetComplete : Boolean = false;
        attribute rangeDemonstrated : Boolean = false;
        attribute latencyDemonstrated : Boolean = false;
        attribute invertedObservationDemonstrated : Boolean = false;
        attribute independentRecoveryComplete : Boolean = false;
        attribute recoveryBlocker : String = "Separate recovery power alone is insufficient: independent host, observation geometry, navigation, antennas and sealed upright/inverted mounting remain unselected. No primary camera/hub credit after shared failure or immersion.";
    }
    part scanningCamera {
        doc /* SC-03: one OAK-1 W IMX378 on Hitec HS785HB azimuth winch, Pololu Micro Maestro6 controller, Pi4B host, powered hub andQKA026 AIS/GPS. Bounded360degree sweep and cable-safe return; splash-only servo requires sealed installation. Revisit delay is unresolved; not credited with simultaneous coverage.*/
        attribute id : String = "SC-03";
        attribute cameraCount : Real = 1;
        attribute horizontalPixels : Real = 4056;
        attribute horizontalFovDeg : Real = 95;
        attribute cameraMassKg : Real = 0.0531;
        attribute servoMassKg : Real = 0.11;
        attribute controllerMassKg : Real = 0.0048;
        attribute servoSupplyV : Real = 6.0;
        attribute servoIdleA : Real = 0.008;
        attribute servoNoLoadA : Real = 0.25;
        attribute servoStallA : Real = 1.8;
        attribute servoSecondsPer60Deg : Real = 1.38;
        attribute idealFullSweepSeconds : Real = 8.28;
        attribute primaryPlanningMassKg : Real = 0.7679;
        attribute installedBudgetComplete : Boolean = false;
        attribute rangeDemonstrated : Boolean = false;
        attribute latencyDemonstrated : Boolean = false;
        attribute invertedObservationDemonstrated : Boolean = false;
        attribute independentRecoveryComplete : Boolean = false;
        attribute recoveryBlocker : String = "Separate recovery power alone is insufficient: independent host, observation geometry, navigation, antennas and sealed upright/inverted mounting remain unselected. No primary camera/hub credit after shared failure or immersion.";
    }
    part underwaterOption {
        doc /* Blue Robotics Ping360 optional submerged sector scanner. Range is supplier instrument range, not weed detection evidence. Adds drag, mount and snag risk. Primary sonar mounted below hull may emerge when inverted; no recovery backup credit.*/
        attribute massWithCableKg : Real = 0.51;
        attribute supplierMaxPowerW : Real = 5.0;
        attribute supplierMaxRangeM : Real = 50.0;
        attribute fullScanAtMaxRangeSeconds : Real = 33.0;
        attribute minimumTemperatureC : Real = 0.0;
        attribute maximumTemperatureC : Real = 30.0;
    }
    part radarReference {
        doc /* Garmin GMRFantom18x is ruled out as an IC01 drop-in: component alone exceeds added mass allocation and electrical demand. Retained as size/power comparison, not an installation candidate.*/
        attribute componentMassKg : Real = 6.35;
        attribute supplierNormalMaxPowerW : Real = 33.0;
        attribute supplierSaveMaxPowerW : Real = 24.0;
        attribute supplierStandbyMaxPowerW : Real = 4.0;
    }
    part budgetBasis {
        doc /* IC01 current base4.5W plus8W increment and1.2kg additional equipment. The full4.5W cannot be freely reassigned if navigation/comms/recording remain. Shared replacements require explicit reconciliation. Recovery battery mass remains separate, recovery electronics/propulsion allocations must not be double-counted.*/
        attribute baseElectronicsW : Real = 4.5;
        attribute additionalSensingW : Real = 8.0;
        attribute additionalEquipmentKg : Real = 1.2;
        attribute aisSupplierMaxW : Real = 0.6;
    }
    part supportAllowances {
        doc /* Unmeasured project planning allowances per primary installation: Pi4B3-6W, powered hub0.3-1W, DC conversion0.90 efficiency; common support mass0.450kg for host, hub, storage, receivers/antennas, wiring, fusing and common case. Ring camera housing/mount allowance0.080kg per camera; scanner sealed bearing/mount allowance0.150kg. These are design targets, not supplier totals. Recovery-side sensing, washing/heating and any structural reinforcement excluded and unresolved.*/
        attribute hostLowW : Real = 3.0;
        attribute hostHighW : Real = 6.0;
        attribute hubLowW : Real = 0.3;
        attribute hubHighW : Real = 1.0;
        attribute conversionEfficiency : Real = 0.9;
        attribute commonPrimaryMassKg : Real = 0.45;
        attribute perFixedCameraHousingKg : Real = 0.08;
        attribute scannerMountKg : Real = 0.15;
    }
}
package BlueDogStudyPlan {
    private import ScalarValues::*;
    part operatingCoverage {
        doc /* Numerical operating coverage, not a new environmental requirement.
         * Eight cases combine two winds, windward/leeward travel and both tacks.
         * State order: speed m/s, true-wind angle, incidence, leeway, rudder, heel;
         * all angles degrees, represented on positive tack and reflected in Python.
         * Incidence coverage is constrained by the recorded aerodynamic grid. */
        attribute windSpeeds : Real [2] ordered = (5, 8);
        attribute stateLower : Real [6] ordered nonunique = (0.2,20,BlueDogAerodynamicPolicy::sizing.incidenceLowDeg,-12,-25,-BlueDogAerodynamicPolicy::sizing.heelLimitDeg);
        attribute stateUpper : Real [6] ordered nonunique = (5,88,BlueDogAerodynamicPolicy::sizing.incidenceHighDeg,12,25,BlueDogAerodynamicPolicy::sizing.heelLimitDeg);
        attribute leewardHeading : Real [2] ordered = (95,175);
        attribute progressSearchReserve : Real = 0.005;
        attribute coarseTrims : Real [2] ordered = (0,90);
        attribute coarseHeels : Real [8] ordered = (-175,-150,-90,-15,15,90,150,175);
        attribute recoveryTrims : Real [4] ordered = (0,90,180,270);
        attribute recoveryDensities : Real [2] ordered = (1000,1025);
        attribute recoveryHeels : Real [3] ordered = (-180,180,49);
        metadata rationale : ModelingMetadata::Rationale { text = "Paired tacks expose the fixed-camber wing asymmetry. Numerical brackets bound a local solve; they do not establish optimality beyond the search domain. Coarse restoring samples screen the search; full-roll free-pitch replay and freshwater/seawater ingress cases assess the candidate. The progress reserve is a mesh allowance, not a physical safety margin."; }
    }
    dependency operatingPurpose from operatingCoverage to BlueDogRequirements::cruiseEvidence;
    dependency recoveryPurpose from operatingCoverage to BlueDogRequirements::selfRighting;
    dependency uncertaintyBasis from operatingCoverage to BlueDogDesignDecisions::uncertaintyPolicy;
}

package BlueDogWindEquipment {
    private import ScalarValues::*;
    private import OOSEM::hardware;
    #hardware part def Installation {
        attribute product : String;
        attribute dataInterface : String;
        attribute sensorMassKg : Real;
        attribute installationAllowanceKg : Real;
        attribute installedMassKg : Real = sensorMassKg + installationAllowanceKg;
        attribute sensorSupplyW : Real;
        attribute interfaceAllowanceW : Real;
        attribute conversionEfficiency : Real;
        attribute powerMargin : Real;
        attribute busPowerW : Real = (sensorSupplyW + interfaceAllowanceW) * powerMargin / conversionEfficiency;
        attribute internalBatteryRuntimeHours : Real;
        attribute xFraction : Real;
        attribute aboveDeckM : Real;
        attribute evidenceAccepted : Boolean = false;
    }
    part testbed : Installation {
        doc /* Historical installation allowance for the retired separate testbed concept.
         * The owned sensor remains available for component experiments; this is
         * not a planned first boat or a selected IC-01 installation. */
        attribute :>> product = "Calypso Ultrasonic Portable Mini";
        attribute :>> dataInterface = "Bluetooth; internal battery; shore Qi charging";
        attribute :>> sensorMassKg = 0.078;
        attribute :>> installationAllowanceKg = 0.05;
        attribute :>> sensorSupplyW = 0;
        attribute :>> interfaceAllowanceW = 0.05;
        attribute :>> conversionEfficiency = 0.9;
        attribute :>> powerMargin = 1.25;
        attribute :>> internalBatteryRuntimeHours = 150;
        attribute :>> xFraction = 0;
        attribute :>> aboveDeckM = 0.3;
        metadata rationale : ModelingMetadata::Rationale { text = "Owner has the battery/Bluetooth sensor originally considered for the retired testbed concept and available for component experiments. Manufacturer lists 78 g including internal battery, 43 mm diameter, 47 mm height, 1 Hz, Bluetooth 5.1, Qi charging and 150 hours active use: https://www.calypsoinstruments.com/shop/ultrasonic-portable-mini-wind-meter-221 . The 50 g mount and 50 mW receiver are project allowances, not product specifications. Sensor energy comes from its own battery; zero vessel-bus sensor power does not mean zero sensor consumption."; }
        metadata issue : ModelingMetadata::Issue { text = "Confirm owned 25 or 45 m/s variant and firmware. Measure runtime, receiver power, disconnection behavior and charging between tests. Internal battery capacity and energy use are not published here; 150 hours is a supplier runtime claim, not an endurance verification."; }
    }
    part challenge : Installation {
        attribute :>> product = "Calypso ULP Wired Mini, 45 m/s UART variant";
        attribute :>> dataInterface = "UART 38400 baud, 1 Hz, 5 V vessel supply";
        attribute :>> sensorMassKg = 0.078;
        attribute :>> installationAllowanceKg = 0.072;
        attribute :>> sensorSupplyW = 5 * 0.00015;
        attribute :>> interfaceAllowanceW = 0.05;
        attribute :>> conversionEfficiency = 0.9;
        attribute :>> powerMargin = 1.25;
        attribute :>> internalBatteryRuntimeHours = 0;
        attribute :>> xFraction = 0;
        attribute :>> aboveDeckM = 0.3;
        metadata rationale : ModelingMetadata::Rationale { text = "Owner restricts the provisional challenge choice to a wired Calypso. The ULP Wired Mini data sheet lists 78 g, 43 by 47 mm, 3.3–5 V, UART, and 0.15 mA at 5 V/38400 baud/1 Hz: https://www.calypsoinstruments.com/web/content/62187?download=true . Select the 45 m/s variant to cover more than the 25 m/s version. The 72 g cable/mount/interface allocation, 50 mW interface draw, 90 percent conversion and 25 percent power margin are project allowances. The generic 2.5 kg equipment and 4.5 W electronics allocations exclude this separately budgeted installation."; }
        metadata issue : ModelingMetadata::Issue { text = "Confirm currently orderable SKU and peak/startup power; 1 Hz data-sheet consumption is not a measured worst case. Qualify weather exposure, immersion and installed-flow errors. Centerline mounting 0.3 m above deck is a mass-centroid placeholder; finalize unobstructed siting and cable layout. Sensor displaced volume and windage remain outside the current geometry model."; }
    }
    dependency challengeSelection from challenge to BlueDogRequirements::windObservation;
    dependency challengeEndurance from challenge to BlueDogRequirements::windSensingEndurance;
    dependency testbedLearning from testbed to BlueDogRequirements::windObservation;
    dependency logicalAllocation from challenge to BlueDog::Architecture::WindSensing;
    analysis Rollup {
        out attribute testbedInstalledMassKg : Real = testbed.installedMassKg;
        out attribute testbedVesselBusW : Real = testbed.busPowerW;
        out attribute testbedSupplierRuntimeHours : Real = testbed.internalBatteryRuntimeHours;
        out attribute challengeInstalledMassKg : Real = challenge.installedMassKg;
        out attribute challengeVesselBusW : Real = challenge.busPowerW;
        out attribute challengeEnergyPerDayWh : Real = challenge.busPowerW * 24;
        out attribute challengeEvidenceAccepted : Boolean = challenge.evidenceAccepted;
    }
}

// Generated by tools.boat_analysis.evidence.model; edit source evidence only through a new recorded run.
package BlueDogRecordedSizing {
    private import ScalarValues::*;
    doc /* Exploratory run at source revision 5ed1a1a78bf2099b71baf455b1a4a47714bc1736.
     * Evidence: evidence/runs/2026-10-10-coupled/manifest.json.
     * This projection preserves the recorded run, not a rerun of the current model. */
    part candidate : MarineDesign::Design {
        attribute :>> length_m = 1.807443825922969;
        attribute :>> beam_m = 0.65429468322854833;
        attribute :>> bottom_depth_m = 0.055209869713076773;
        attribute :>> deck_height_m = 0.11736969654075137;
        attribute :>> sail_m2 = 1.2797103004630528;
        attribute :>> sail_AR = 3.9980406361782688;
        attribute :>> camber_scale = 1.0887307817804102;
        attribute :>> wing_thickness_scale = 2;
        attribute :>> mast_fraction = 0.50514999095613922;
        attribute :>> mast_x_fraction = -0.014819264906112906;
        attribute :>> keel_m2 = 0.15414394281400351;
        attribute :>> keel_span_m = 0.73366559778329299;
        attribute :>> rudder_m2 = 0.0065043362556077358;
        attribute :>> rudder_span_m = 0.094949450801005628;
        attribute :>> rudder_arm_fraction = 0.65000000000000002;
        attribute :>> ballast_kg = 11.419036101104718;
        attribute :>> battery_Wh = 202.04795208249863;
        attribute :>> panel_m2 = 0.22484226038869715;
        attribute :>> wing_torque_Nm = 1.47400775527911;
        attribute :>> rudder_torque_Nm = 0.050000000000000003;
        attribute :>> hull_glass_kg_m2 = 0.43732697228578921;
        attribute :>> wing_glass_kg_m2 = 0.41837175232357449;
        attribute :>> keel_glass_kg_m2 = 5.177595530680474;
        attribute :>> rudder_glass_kg_m2 = 1.2624198475095523;
        attribute :>> hull_rib_pitch_m = 0.02168468045316662;
        attribute :>> foil_rib_pitch_m = 0.22996551066596616;
        attribute :>> battery_x_fraction = -0.3492051574654379;
        attribute :>> battery_z_fraction = 0.050000000000000003;
        attribute :>> hull_fullness_exponent = 2;
    }
    part nominal : BlueDogSizingEvidence::Scenario {
        attribute :>> label = "nominal";
        attribute :>> numericallyBalanced = true;
        attribute :>> missingPitchRoots = 0;
        attribute :>> pitchUnstableSamples = 86;
        attribute :>> diagnosticControlCases = 0;
        attribute :>> easterlyHours = 67.95286846237228;
        attribute :>> westerlyHours = 54.899322200049156;
        attribute :>> massKg = 31.447719266406427;
        attribute :>> evidenceAccepted = false;
        attribute :>> operatingMargins = (-2.7542028657734363e-09);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.3539169888293774,0.0065694861937930504,0.056210160244829499,3.0065694861937935,0.35391698882937783,0.23750941388820612);
        attribute :>> restoringMomentsNm = (22.493872954339402,24.158515344731363,22.498170811429766,24.100789441545356);
    }
    analysis nominalReview : BlueDogSizingEvidence::Review { subject :>> scenario = nominal; }
    part construction : BlueDogSizingEvidence::Scenario {
        attribute :>> label = "construction";
        attribute :>> numericallyBalanced = true;
        attribute :>> missingPitchRoots = 0;
        attribute :>> pitchUnstableSamples = 86;
        attribute :>> diagnosticControlCases = 0;
        attribute :>> easterlyHours = 68.963211336291593;
        attribute :>> westerlyHours = 55.9130957861287;
        attribute :>> massKg = 33.105645195552896;
        attribute :>> evidenceAccepted = false;
        attribute :>> operatingMargins = (-2.729905190790305e-13);
        attribute :>> structuralMargins = (0.92774058392461622,0.582530459248499,0.71651081726844024,0.30233550151466004,0.85626285066536822,-0.25899904624574943,-0.37490864339433827,-0.34306198499446139,0.73466202647425916,0.027406709157772324,0.25417528189148164,0.67350924431629999,-0.022478676976586565,0.88775113773194525,1.3104061488983119,0.80441256912775128,0.25922506131558137,1.1005009742727014,0.96275800136512646,0.96274558049686976,0.18037988867479504,0.26013957342803928);
        attribute :>> routeMargins = (3.3230767022011154,-0.0099216408359179553,0.042177620329283405,2.990078359164082,0.32307670220111584,0.22342922519265696);
        attribute :>> restoringMomentsNm = (22.647259365581739,24.40436521217109,22.65182068067374,24.343117811403939);
    }
    analysis constructionReview : BlueDogSizingEvidence::Review { subject :>> scenario = construction; }
    part aerodynamic : BlueDogSizingEvidence::Scenario {
        attribute :>> label = "aerodynamic";
        attribute :>> numericallyBalanced = true;
        attribute :>> missingPitchRoots = 0;
        attribute :>> pitchUnstableSamples = 86;
        attribute :>> diagnosticControlCases = 0;
        attribute :>> easterlyHours = 91.881941680698603;
        attribute :>> westerlyHours = 56.868141417534666;
        attribute :>> massKg = 31.447719266406427;
        attribute :>> evidenceAccepted = false;
        attribute :>> operatingMargins = (-2.3098361197071425e-08);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.327026185423728,-0.29714538578115279,-0.27613807889859165,2.7028546142188472,0.32702618542372841,0.2101647025342408);
        attribute :>> restoringMomentsNm = (22.493872954339402,24.158515344731363,22.498170811429766,24.100789441545356);
    }
    analysis aerodynamicReview : BlueDogSizingEvidence::Review { subject :>> scenario = aerodynamic; }
    part hydrodynamic : BlueDogSizingEvidence::Scenario {
        attribute :>> label = "hydrodynamic";
        attribute :>> numericallyBalanced = true;
        attribute :>> missingPitchRoots = 0;
        attribute :>> pitchUnstableSamples = 86;
        attribute :>> diagnosticControlCases = 0;
        attribute :>> easterlyHours = 72.348545855704302;
        attribute :>> westerlyHours = 58.322366218346858;
        attribute :>> massKg = 31.447719266406427;
        attribute :>> evidenceAccepted = false;
        attribute :>> operatingMargins = (-5.2153836804791358e-13);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.2566035818493404,-0.063095581478009866,-0.0048409146625596478,2.9369044185219901,0.25660358184934084,0.18996713585629366);
        attribute :>> restoringMomentsNm = (22.493872954339402,24.158515344731363,22.498170811429766,24.100789441545356);
    }
    analysis hydrodynamicReview : BlueDogSizingEvidence::Review { subject :>> scenario = hydrodynamic; }
    part energy : BlueDogSizingEvidence::Scenario {
        attribute :>> label = "energy";
        attribute :>> numericallyBalanced = true;
        attribute :>> missingPitchRoots = 0;
        attribute :>> pitchUnstableSamples = 86;
        attribute :>> diagnosticControlCases = 8;
        attribute :>> easterlyHours = 67.936040275364761;
        attribute :>> westerlyHours = 54.725803496072416;
        attribute :>> massKg = 31.447719266406427;
        attribute :>> evidenceAccepted = false;
        attribute :>> operatingMargins = (-0.59538548401096325);
        attribute :>> structuralMargins = (0.94543513836936344,0.66837739039140598,0.793811093735875,0.48102813749816431,0.89146433697702698,8.0834283378017346e-08,-6.0907544834343241e-06,0.00093615008183722814,0.75999985862045649,-8.8362227712579511e-07,0.30885760961849151,0.69084260925563856,-1.5261190828841364e-06,0.90378668948452445,1.3527871062958945,0.89954132424960243,0.26099093454048067,1.1005009742727014,0.96403951655735221,0.96516596775583285,0.2734454024019124,0.33245330386656824);
        attribute :>> routeMargins = (3.3596666637101062,0.0065694861769212132,0.056443885064378363,3.0065694861769217,0.35966666371010625,0.23991939588788314);
        attribute :>> restoringMomentsNm = (22.493872954339402,24.158515344731363,22.498170811429766,24.100789441545356);
    }
    analysis energyReview : BlueDogSizingEvidence::Review { subject :>> scenario = energy; }
    part combined : BlueDogSizingEvidence::Scenario {
        attribute :>> label = "combined";
        attribute :>> numericallyBalanced = true;
        attribute :>> missingPitchRoots = 0;
        attribute :>> pitchUnstableSamples = 86;
        attribute :>> diagnosticControlCases = 8;
        attribute :>> easterlyHours = 3842.0473089633233;
        attribute :>> westerlyHours = 106.52360358013347;
        attribute :>> massKg = 33.105645195552896;
        attribute :>> evidenceAccepted = false;
        attribute :>> operatingMargins = (-0.59537663254393447);
        attribute :>> structuralMargins = (0.92774058392461622,0.582530459248499,0.71651081726844024,0.30233550151466004,0.85626285066536822,-0.25899904624574943,-0.37490864339433827,-0.34306198499446139,0.73466202647425916,0.027406709157772324,0.25417528189148164,0.67350924431629999,-0.022478676976586565,0.88775113773194525,1.3104061488983119,0.80441256912775128,0.25922506131558137,1.1005009742727014,0.96275800136512646,0.96274558049686976,0.18037988867479504,0.26013957342803928);
        attribute :>> routeMargins = (3.5994024503321409,-0.98549451350569939,-52.361768180046155,3.0145054864943006,-0.40059754966785954,-0.47949449416852041);
        attribute :>> restoringMomentsNm = (22.647259365581739,24.40436521217109,22.65182068067374,24.343117811403939);
    }
    analysis combinedReview : BlueDogSizingEvidence::Review { subject :>> scenario = combined; }
    dependency candidateBasis from candidate to BlueDogDesignDecisions::sizingBaseline;
}

// Generated by tools.boat_analysis.evidence.model; edit source evidence only through a new recorded run.
package BlueDogCurrentSizing {
    private import ScalarValues::*;
    doc /* Exploratory run at source revision 6716c9a12301ba3c91d1ceb2190de4ef00a884f9.
     * Evidence: evidence/runs/2026-10-12-bingen/manifest.json.
     * Finite Gorge challenge rerun; publishing this projection does not execute a new solve. */
    part candidate : MarineDesign::Design {
        attribute :>> length_m = 2.009273606288621;
        attribute :>> beam_m = 0.60794480099882087;
        attribute :>> bottom_depth_m = 0.052980023908892906;
        attribute :>> deck_height_m = 0.16285437007218445;
        attribute :>> sail_m2 = 1.1749947436992398;
        attribute :>> sail_AR = 2.9897220605843415;
        attribute :>> camber_scale = 1.0001651734277246;
        attribute :>> wing_thickness_scale = 1.2029291216922127;
        attribute :>> mast_fraction = 0.50015640304676856;
        attribute :>> mast_x_fraction = -0.017055895322377945;
        attribute :>> keel_m2 = 0.14785705608104413;
        attribute :>> keel_span_m = 0.70810230340354718;
        attribute :>> rudder_m2 = 0.01250616472159935;
        attribute :>> rudder_span_m = 0.12822691546838755;
        attribute :>> rudder_arm_fraction = 0.49984320901592999;
        attribute :>> ballast_kg = 11.668930280578605;
        attribute :>> battery_Wh = 208.20669848542397;
        attribute :>> panel_m2 = 0.23097609955017351;
        attribute :>> wing_torque_Nm = 0.84581422481627055;
        attribute :>> rudder_torque_Nm = 0.81439501073520648;
        attribute :>> hull_glass_kg_m2 = 0.60341709609082861;
        attribute :>> wing_glass_kg_m2 = 0.45241145604172167;
        attribute :>> keel_glass_kg_m2 = 4.80809991405666;
        attribute :>> rudder_glass_kg_m2 = 0.60281995032794811;
        attribute :>> hull_rib_pitch_m = 0.029734176171558116;
        attribute :>> foil_rib_pitch_m = 0.04046312096151844;
        attribute :>> battery_x_fraction = -0.34649999999999992;
        attribute :>> battery_z_fraction = 0.099963514620108593;
        attribute :>> hull_fullness_exponent = 1.8000691642287374;
    }
    part searchAssessment {
        attribute solverStatus : String = "Iteration limit reached";
        attribute activeBounds : String = "none";
        attribute coarseFeasible : Boolean = true;
        attribute massKg : Real = 33.441655552026205;
        attribute maximumResidual : Real = 1.9663214043119659e-08;
        attribute minimumMargin : Real = -1.2707505936404573e-08;
        attribute progressReserveMps : Real = 0.0050000000000000001;
        attribute qualified : Boolean = false;
    }
    part searchConstraint0 {
        attribute label : String = "keelDeflectionMargin";
        attribute margin : Real = -1.2707505936404573e-08;
    }
    part searchConstraint1 {
        attribute label : String = "wingDeflectionMargin";
        attribute margin : Real = -7.6129478276953932e-09;
    }
    part searchConstraint2 {
        attribute label : String = "case 4: wingDriveMargin";
        attribute margin : Real = -2.9918589827815367e-09;
    }
    part searchConstraint3 {
        attribute label : String = "case 0: delftDomain6 (search reserve)";
        attribute margin : Real = 0;
    }
    part searchConstraint4 {
        attribute label : String = "case 1: delftDomain6 (search reserve)";
        attribute margin : Real = 0;
    }
    part searchConstraint5 {
        attribute label : String = "case 2: delftDomain6 (search reserve)";
        attribute margin : Real = 0;
    }
    part searchConstraint6 {
        attribute label : String = "case 3: delftDomain6 (search reserve)";
        attribute margin : Real = 0;
    }
    part searchConstraint7 {
        attribute label : String = "case 4: delftDomain6 (search reserve)";
        attribute margin : Real = 0;
    }
    part searchConstraint8 {
        attribute label : String = "case 5: delftDomain6 (search reserve)";
        attribute margin : Real = 0;
    }
    part searchConstraint9 {
        attribute label : String = "case 6: delftDomain6 (search reserve)";
        attribute margin : Real = 0;
    }
    part searchConstraint10 {
        attribute label : String = "case 7: delftDomain6 (search reserve)";
        attribute margin : Real = 0;
    }
    part searchConstraint11 {
        attribute label : String = "case 0: delftDomain15 (search reserve)";
        attribute margin : Real = 0.0020000000000154339;
    }
    part convergence0 {
        attribute label : String = "forward, beta 0, wake";
        attribute passesScreen : Boolean = true;
        attribute CLtot : Real = 0.0010974820100000393;
        attribute CDi : Real = 0.00084670703500000499;
        attribute CMytot : Real = 0.00020432221599998857;
    }
    part convergence1 {
        attribute label : String = "forward, beta 0, mesh";
        attribute passesScreen : Boolean = true;
        attribute CLtot : Real = 0.017708813035000048;
        attribute CDi : Real = 0.0064258317499999995;
        attribute CMytot : Real = 0.0031552284759999993;
    }
    part convergence2 {
        attribute label : String = "reverse, beta 0, wake";
        attribute passesScreen : Boolean = true;
        attribute CLtot : Real = 0.001327419566000021;
        attribute CDi : Real = 0.00085670971500000082;
        attribute CMytot : Real = 0.00024245977799999818;
    }
    part convergence3 {
        attribute label : String = "reverse, beta 0, mesh";
        attribute passesScreen : Boolean = true;
        attribute CLtot : Real = 0.020571112351000065;
        attribute CDi : Real = 0.0053078105269999953;
        attribute CMytot : Real = 0.0033816664710000222;
    }
    part convergence4 {
        attribute label : String = "forward, beta 20, wake";
        attribute passesScreen : Boolean = true;
        attribute CLtot : Real = 0.0030444152249999856;
        attribute CDi : Real = 0.00093538887700000961;
        attribute CMytot : Real = 0.00074289939299999885;
    }
    part convergence5 {
        attribute label : String = "forward, beta 20, mesh";
        attribute passesScreen : Boolean = true;
        attribute CLtot : Real = 0.015921558743000053;
        attribute CDi : Real = 0.0030920898859999879;
        attribute CMytot : Real = 0.0028109218799999974;
    }
    part coarseGrid0 {
        attribute label : String = "forward, beta 0: mesh 24/wake 5 to mesh 72/wake 30";
        attribute CLtot : Real = 0.050497159055000074;
        attribute CDi : Real = 0.007092610272000005;
        attribute CMytot : Real = 0.0098591795550000139;
    }
    part coarseGrid1 {
        attribute label : String = "reverse, beta 0: mesh 24/wake 5 to mesh 72/wake 30";
        attribute CLtot : Real = 0.065062912521000049;
        attribute CDi : Real = 0.0035108145999999951;
        attribute CMytot : Real = 0.011013893448000023;
    }
    part coarseGrid2 {
        attribute label : String = "forward, beta 20: mesh 24/wake 5 to mesh 72/wake 30";
        attribute CLtot : Real = 0.048231737603000036;
        attribute CDi : Real = 0.0029270257569999902;
        attribute CMytot : Real = 0.0088007662020000016;
    }
    dependency assumptions from candidate to BlueDogAerodynamicPolicy::sizing;
    dependency convergenceBasis from convergence0 to BlueDogAerodynamicPolicy::convergenceInputs;
    part ingress0 {
        attribute label : String = "sealed, water 1000 kg/m3";
        attribute minimumRestoringNm : Real = 20.461024795165429;
        attribute missingPitchRoots : Integer = 0;
        attribute unstablePitchSamples : Integer = 78;
        attribute retainedWaterKg : Real = 0;
    }
    dependency ingressBasis0 from ingress0 to BlueDogRequirements::selfRighting;
    part ingress1 {
        attribute label : String = "free_flooding_homogenized, water 1000 kg/m3";
        attribute minimumRestoringNm : Real = -7.49090747036204;
        attribute missingPitchRoots : Integer = 0;
        attribute unstablePitchSamples : Integer = 0;
        attribute retainedWaterKg : Real = 0;
    }
    dependency ingressBasis1 from ingress1 to BlueDogRequirements::selfRighting;
    part ingress2 {
        attribute label : String = "full_water_retention, water 1000 kg/m3";
        attribute minimumRestoringNm : Real = -412.1378752582504;
        attribute missingPitchRoots : Integer = 0;
        attribute unstablePitchSamples : Integer = 7;
        attribute retainedWaterKg : Real = 46.16821699317093;
    }
    dependency ingressBasis2 from ingress2 to BlueDogRequirements::selfRighting;
    part ingress3 {
        attribute label : String = "sealed, water 1025 kg/m3";
        attribute minimumRestoringNm : Real = 20.666808275804474;
        attribute missingPitchRoots : Integer = 0;
        attribute unstablePitchSamples : Integer = 78;
        attribute retainedWaterKg : Real = 0;
    }
    dependency ingressBasis3 from ingress3 to BlueDogRequirements::selfRighting;
    part ingress4 {
        attribute label : String = "free_flooding_homogenized, water 1025 kg/m3";
        attribute minimumRestoringNm : Real = -7.8540319493918229;
        attribute missingPitchRoots : Integer = 0;
        attribute unstablePitchSamples : Integer = 0;
        attribute retainedWaterKg : Real = 0;
    }
    dependency ingressBasis4 from ingress4 to BlueDogRequirements::selfRighting;
    part ingress5 {
        attribute label : String = "full_water_retention, water 1025 kg/m3";
        attribute minimumRestoringNm : Real = -424.31304856120465;
        attribute missingPitchRoots : Integer = 0;
        attribute unstablePitchSamples : Integer = 7;
        attribute retainedWaterKg : Real = 47.322422418000208;
    }
    dependency ingressBasis5 from ingress5 to BlueDogRequirements::selfRighting;
    part nominal : BlueDogSizingEvidence::Scenario {
        attribute :>> label = "primary";
        attribute limitingScreens : String = "keelDeflectionMargin: -1.271e-08; wingDeflectionMargin: -7.613e-09; operating/peak power: -4.452e-13";
        attribute easterlyDownstreamMps : Real = 2.0648992805241333;
        attribute easterlyUpstreamMps : Real = 0.24861053884093698;
        attribute easterlyTimeLabel : String = if not numericallyBalanced or diagnosticControlCases > 0 ? "Diagnostic only" else if easterlyDownstreamMps <= 0 or easterlyUpstreamMps <= 0 ? "No completion (duration penalty)" else "41.18";
        attribute westerlyDownstreamMps : Real = 1.748610538840937;
        attribute westerlyUpstreamMps : Real = 0.5648992805241333;
        attribute westerlyTimeLabel : String = if not numericallyBalanced or diagnosticControlCases > 0 ? "Diagnostic only" else if westerlyDownstreamMps <= 0 or westerlyUpstreamMps <= 0 ? "No completion (duration penalty)" else "21.4";
        attribute :>> acceptanceRouteMargins = (2.497221077681874,0.12979856104826659,1);
        attribute :>> numericallyBalanced = true;
        attribute :>> missingPitchRoots = 0;
        attribute :>> pitchUnstableSamples = 78;
        attribute :>> diagnosticControlCases = 0;
        attribute :>> easterlyHours = 41.177205555190881;
        attribute :>> westerlyHours = 21.399871474949084;
        attribute :>> massKg = 33.451612629662762;
        attribute :>> evidenceAccepted = false;
        attribute :>> operatingMargins = (-4.4519943287468777e-13);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.1297985610482666,-0.50277892231812604,1,2.497221077681874,0.12979856104826659,1);
        attribute :>> restoringMomentsNm = (20.461024795165429,22.56743407497024,20.461140176385193,22.516756516316924);
    }
    analysis nominalReview : BlueDogSizingEvidence::Review { subject :>> scenario = nominal; }
    part construction : BlueDogSizingEvidence::Scenario {
        attribute :>> label = "construction";
        attribute limitingScreens : String = "keelDeflectionMargin: -0.3672; wingDeflectionMargin: -0.2598; rudderDeflectionMargin: -0.2325";
        attribute easterlyDownstreamMps : Real = 2.0285980753275306;
        attribute easterlyUpstreamMps : Real = 0.22571351097759995;
        attribute easterlyTimeLabel : String = if not numericallyBalanced or diagnosticControlCases > 0 ? "Diagnostic only" else if easterlyDownstreamMps <= 0 or easterlyUpstreamMps <= 0 ? "No completion (duration penalty)" else "44.98";
        attribute westerlyDownstreamMps : Real = 1.7257135109776001;
        attribute westerlyUpstreamMps : Real = 0.52859807532753078;
        attribute westerlyTimeLabel : String = if not numericallyBalanced or diagnosticControlCases > 0 ? "Diagnostic only" else if westerlyDownstreamMps <= 0 or westerlyUpstreamMps <= 0 ? "No completion (duration penalty)" else "22.58";
        attribute :>> acceptanceRouteMargins = (2.4514270219552001,0.057196150655061562,1);
        attribute :>> numericallyBalanced = true;
        attribute :>> missingPitchRoots = 0;
        attribute :>> pitchUnstableSamples = 76;
        attribute :>> diagnosticControlCases = 8;
        attribute :>> easterlyHours = 44.984646165700134;
        attribute :>> westerlyHours = 22.579982312648262;
        attribute :>> massKg = 35.19377680849091;
        attribute :>> evidenceAccepted = false;
        attribute :>> operatingMargins = (-0.0034497945894563786);
        attribute :>> structuralMargins = (0.95012551241916643,0.60697490766656381,0.70972900347325729,0.3250231564189493,0.91059709471054695,-0.25983237493429878,-0.36716555113396177,-0.23251048749892167,0.73795101563745258,0.045434182010065771,0.15230478798236058,0.63301191953702252,-0.015898106704652415,0.88432961195254223,2.190155342363703,1.3321889009175707,0.28054565813084908,1.1737992819589698,0.96795978558604012,0.92827778730948429,0.21400460169919389,0.68264105810567521);
        attribute :>> routeMargins = (3.0571961506550611,-0.5485729780448001,1,2.4514270219552001,0.057196150655061562,1);
        attribute :>> restoringMomentsNm = (20.562926296637674,22.766759478829695,20.563048977595543,22.712750472442298);
    }
    analysis constructionReview : BlueDogSizingEvidence::Review { subject :>> scenario = construction; }
    part aerodynamic : BlueDogSizingEvidence::Scenario {
        attribute :>> label = "aerodynamic";
        attribute limitingScreens : String = "keelDeflectionMargin: -1.271e-08; wingDeflectionMargin: -7.613e-09; operating/peak power: -1.56e-11";
        attribute easterlyDownstreamMps : Real = 2.0500996813609271;
        attribute easterlyUpstreamMps : Real = -0.0013020451514235143;
        attribute easterlyTimeLabel : String = if not numericallyBalanced or diagnosticControlCases > 0 ? "Diagnostic only" else if easterlyDownstreamMps <= 0 or easterlyUpstreamMps <= 0 ? "No completion (duration penalty)" else "1e+06";
        attribute westerlyDownstreamMps : Real = 1.4986979548485766;
        attribute westerlyUpstreamMps : Real = 0.55009968136092691;
        attribute westerlyTimeLabel : String = if not numericallyBalanced or diagnosticControlCases > 0 ? "Diagnostic only" else if westerlyDownstreamMps <= 0 or westerlyUpstreamMps <= 0 ? "No completion (duration penalty)" else "22.71";
        attribute :>> acceptanceRouteMargins = (1.9973959096971532,0.10019936272185381,1);
        attribute :>> numericallyBalanced = true;
        attribute :>> missingPitchRoots = 0;
        attribute :>> pitchUnstableSamples = 78;
        attribute :>> diagnosticControlCases = 0;
        attribute :>> easterlyHours = 1000000;
        attribute :>> westerlyHours = 22.706358340193432;
        attribute :>> massKg = 33.451612629662762;
        attribute :>> evidenceAccepted = false;
        attribute :>> operatingMargins = (-1.5596857139144049e-11);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.1001993627218543,-1.002604090302847,1,1.9973959096971532,0.10019936272185381,1);
        attribute :>> restoringMomentsNm = (20.461024795165429,22.56743407497024,20.461140176385193,22.516756516316924);
    }
    analysis aerodynamicReview : BlueDogSizingEvidence::Review { subject :>> scenario = aerodynamic; }
    part hydrodynamic : BlueDogSizingEvidence::Scenario {
        attribute :>> label = "hydrodynamic";
        attribute limitingScreens : String = "keelDeflectionMargin: -1.271e-08; wingDeflectionMargin: -7.613e-09; operating/peak power: -3.043e-11";
        attribute easterlyDownstreamMps : Real = 2.0334428096828874;
        attribute easterlyUpstreamMps : Real = 0.22652611415453172;
        attribute easterlyTimeLabel : String = if not numericallyBalanced or diagnosticControlCases > 0 ? "Diagnostic only" else if easterlyDownstreamMps <= 0 or easterlyUpstreamMps <= 0 ? "No completion (duration penalty)" else "44.83";
        attribute westerlyDownstreamMps : Real = 1.7265261141545318;
        attribute westerlyUpstreamMps : Real = 0.53344280968288738;
        attribute westerlyTimeLabel : String = if not numericallyBalanced or diagnosticControlCases > 0 ? "Diagnostic only" else if westerlyDownstreamMps <= 0 or westerlyUpstreamMps <= 0 ? "No completion (duration penalty)" else "22.42";
        attribute :>> acceptanceRouteMargins = (2.4530522283090637,0.066885619365774751,1);
        attribute :>> numericallyBalanced = true;
        attribute :>> missingPitchRoots = 0;
        attribute :>> pitchUnstableSamples = 78;
        attribute :>> diagnosticControlCases = 0;
        attribute :>> easterlyHours = 44.828701650274091;
        attribute :>> westerlyHours = 22.420504524115525;
        attribute :>> massKg = 33.451612629662762;
        attribute :>> evidenceAccepted = false;
        attribute :>> operatingMargins = (-3.0432767417210016e-11);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.0668856193657748,-0.54694777169093656,1,2.4530522283090637,0.066885619365774751,1);
        attribute :>> restoringMomentsNm = (20.461024795165429,22.56743407497024,20.461140176385193,22.516756516316924);
    }
    analysis hydrodynamicReview : BlueDogSizingEvidence::Review { subject :>> scenario = hydrodynamic; }
    part energy : BlueDogSizingEvidence::Scenario {
        attribute :>> label = "energy";
        attribute limitingScreens : String = "keelDeflectionMargin: -1.271e-08; wingDeflectionMargin: -7.613e-09; operating/peak power: -4.452e-13";
        attribute easterlyDownstreamMps : Real = 2.0648992805241333;
        attribute easterlyUpstreamMps : Real = 0.24861053884093698;
        attribute easterlyTimeLabel : String = if not numericallyBalanced or diagnosticControlCases > 0 ? "Diagnostic only" else if easterlyDownstreamMps <= 0 or easterlyUpstreamMps <= 0 ? "No completion (duration penalty)" else "41.18";
        attribute westerlyDownstreamMps : Real = 1.748610538840937;
        attribute westerlyUpstreamMps : Real = 0.5648992805241333;
        attribute westerlyTimeLabel : String = if not numericallyBalanced or diagnosticControlCases > 0 ? "Diagnostic only" else if westerlyDownstreamMps <= 0 or westerlyUpstreamMps <= 0 ? "No completion (duration penalty)" else "21.4";
        attribute :>> acceptanceRouteMargins = (2.497221077681874,0.12979856104826659,1);
        attribute :>> numericallyBalanced = true;
        attribute :>> missingPitchRoots = 0;
        attribute :>> pitchUnstableSamples = 78;
        attribute :>> diagnosticControlCases = 0;
        attribute :>> easterlyHours = 41.177205555190881;
        attribute :>> westerlyHours = 21.399871474949084;
        attribute :>> massKg = 33.451612629662762;
        attribute :>> evidenceAccepted = false;
        attribute :>> operatingMargins = (-4.4519943287468777e-13);
        attribute :>> structuralMargins = (0.96232046666456039,0.68797127438754957,0.78768408845980287,0.47436189159818165,0.93246005802610732,-7.6129478276953932e-09,-1.2707505936404573e-08,0.040182656049085219,0.76297477341939546,0.018534601818054219,0.21518622194779502,0.64969800630459118,0.0041543100012498835,0.90085395310217908,2.2319079760072187,1.4536495912113572,0.2822853511993289,1.1737992819589698,0.9694571871275337,0.9321174247116053,0.30103041231927197,0.70697633910527957);
        attribute :>> routeMargins = (3.1297985610482666,-0.50277892231812604,1,2.497221077681874,0.12979856104826659,1);
        attribute :>> restoringMomentsNm = (20.461024795165429,22.56743407497024,20.461140176385193,22.516756516316924);
    }
    analysis energyReview : BlueDogSizingEvidence::Review { subject :>> scenario = energy; }
    part combined : BlueDogSizingEvidence::Scenario {
        attribute :>> label = "combined";
        attribute limitingScreens : String = "westerly upstream progress: -0.6815; keelDeflectionMargin: -0.3672; wingDeflectionMargin: -0.2598";
        attribute easterlyDownstreamMps : Real = 2.1592714175795447;
        attribute easterlyUpstreamMps : Real = -0.34895710869965768;
        attribute easterlyTimeLabel : String = if not numericallyBalanced or diagnosticControlCases > 0 ? "Diagnostic only" else if easterlyDownstreamMps <= 0 or easterlyUpstreamMps <= 0 ? "No completion (duration penalty)" else "1e+06";
        attribute westerlyDownstreamMps : Real = 1.6510428913003423;
        attribute westerlyUpstreamMps : Real = 0.15927141757954466;
        attribute westerlyTimeLabel : String = if not numericallyBalanced or diagnosticControlCases > 0 ? "Diagnostic only" else if westerlyDownstreamMps <= 0 or westerlyUpstreamMps <= 0 ? "No completion (duration penalty)" else "62.9";
        attribute :>> acceptanceRouteMargins = (2.3020857826006846,-0.68145716484091068,1);
        attribute :>> numericallyBalanced = true;
        attribute :>> missingPitchRoots = 0;
        attribute :>> pitchUnstableSamples = 76;
        attribute :>> diagnosticControlCases = 8;
        attribute :>> easterlyHours = 1000000;
        attribute :>> westerlyHours = 62.901603115984216;
        attribute :>> massKg = 35.19377680849091;
        attribute :>> evidenceAccepted = false;
        attribute :>> operatingMargins = (-0.0034497945894563786);
        attribute :>> structuralMargins = (0.95012551241916643,0.60697490766656381,0.70972900347325729,0.3250231564189493,0.91059709471054695,-0.25983237493429878,-0.36716555113396177,-0.23251048749892167,0.73795101563745258,0.045434182010065771,0.15230478798236058,0.63301191953702252,-0.015898106704652415,0.88432961195254223,2.190155342363703,1.3321889009175707,0.28054565813084908,1.1737992819589698,0.96795978558604012,0.92827778730948429,0.21400460169919389,0.68264105810567521);
        attribute :>> routeMargins = (3.3185428351590893,-1.6979142173993154,1,2.3020857826006846,-0.68145716484091068,1);
        attribute :>> restoringMomentsNm = (20.562926296637674,22.766759478829695,20.563048977595543,22.712750472442298);
    }
    analysis combinedReview : BlueDogSizingEvidence::Review { subject :>> scenario = combined; }
    dependency candidateBasis from candidate to BlueDogDesignDecisions::sizingBaseline;
}

// Generated by tools.boat_analysis.evidence.continuation.
package BlueDogFinitePassageSizing {
    private import ScalarValues::*;
    doc /* Coarse fixed-length feasibility only; no refined replay or physical qualification.
     * Hull length does not bound the full vessel footprint. Appendage geometry/model applicability,
     * chronological voyage energy and free-pitch dynamic recovery require further assessment. */
    part summary {
        attribute targetM : Real = 1.3;
        attribute smallestFeasibleM : Real = 1.4;
        attribute targetReached : Boolean = false;
        attribute qualified : Boolean = false;
    }
    attribute evidenceManifest : String = "evidence/runs/2026-10-12-finite-passage/manifest.json";
    attribute stageNames : String [*] ordered nonunique = ("BlueDogFinitePassageSizing::stage0", "BlueDogFinitePassageSizing::stage1", "BlueDogFinitePassageSizing::stage2", "BlueDogFinitePassageSizing::stage3");
    part stage0 {
        attribute lengthM : Real = 2.0;
        attribute feasible : Boolean = true;
        attribute maximumResidual : Real = 4.182576190459031e-06;
        attribute minimumMargin : Real = -1.1025578690260218e-05;
        attribute massKg : Real = 34.52412299851067;
        attribute batteryWh : Real = 325.2078173450327;
        attribute sweptLengthM : Real = 2.055134910550832;
    }
    part stage1 {
        attribute lengthM : Real = 1.8;
        attribute feasible : Boolean = true;
        attribute maximumResidual : Real = 7.595253901313548e-05;
        attribute minimumMargin : Real = -1.2385637890588442e-05;
        attribute massKg : Real = 33.892094215193396;
        attribute batteryWh : Real = 336.57874745676276;
        attribute sweptLengthM : Real = 1.855512367580499;
    }
    part stage2 {
        attribute lengthM : Real = 1.6;
        attribute feasible : Boolean = true;
        attribute maximumResidual : Real = 1.282076064796911e-05;
        attribute minimumMargin : Real = -5.497405316079451e-05;
        attribute massKg : Real = 32.03456052626014;
        attribute batteryWh : Real = 339.4534569423761;
        attribute sweptLengthM : Real = 1.6560166270489536;
    }
    part stage3 {
        attribute lengthM : Real = 1.4;
        attribute feasible : Boolean = true;
        attribute maximumResidual : Real = 8.609802684258482e-05;
        attribute minimumMargin : Real = -3.352359621455747e-06;
        attribute massKg : Real = 29.88859101991109;
        attribute batteryWh : Real = 342.8229703130181;
        attribute sweptLengthM : Real = 1.4572906057700608;
    }
    part candidate : MarineDesign::Design {
        attribute :>> length_m = 1.4;
        attribute :>> beam_m = 0.5067999999997308;
        attribute :>> bottom_depth_m = 0.07825454337382551;
        attribute :>> deck_height_m = 0.07884291230310685;
        attribute :>> sail_m2 = 1.226228622011194;
        attribute :>> sail_AR = 2.257707673201315;
        attribute :>> camber_scale = 1.1269456057834304;
        attribute :>> wing_thickness_scale = 1.169694656497319;
        attribute :>> mast_fraction = 0.5162169792322526;
        attribute :>> mast_x_fraction = -0.02348623882263623;
        attribute :>> keel_m2 = 0.13506170600262693;
        attribute :>> keel_span_m = 0.663912474887663;
        attribute :>> rudder_m2 = 0.026262017317854536;
        attribute :>> rudder_span_m = 0.22920003170553543;
        attribute :>> rudder_arm_fraction = 0.5;
        attribute :>> ballast_kg = 12.052274648770574;
        attribute :>> battery_Wh = 342.8229703130181;
        attribute :>> panel_m2 = 0.2032306262224013;
        attribute :>> wing_torque_Nm = 3.492899663850968;
        attribute :>> rudder_torque_Nm = 0.7214713371678395;
        attribute :>> hull_glass_kg_m2 = 0.5154764183265355;
        attribute :>> wing_glass_kg_m2 = 0.2;
        attribute :>> keel_glass_kg_m2 = 4.781689503948721;
        attribute :>> rudder_glass_kg_m2 = 1.3034445787692075;
        attribute :>> hull_rib_pitch_m = 0.025559690195011968;
        attribute :>> foil_rib_pitch_m = 0.06512394400281599;
        attribute :>> battery_x_fraction = -0.3464999999999999;
        attribute :>> battery_z_fraction = 0.09316939078359278;
        attribute :>> hull_fullness_exponent = 1.8071152832027766;
    }
    dependency basis from candidate to BlueDogDesignDecisions::sizingBaseline;
    part assessment {
        attribute massKg : Real = 29.88859101991109;
        attribute westerlyHours : Real = 23.779129978035403;
        attribute rudderChordM : Real = candidate.rudder_m2 / candidate.rudder_span_m;
        attribute rudderAspectRatio : Real = candidate.rudder_span_m * candidate.rudder_span_m / candidate.rudder_m2;
        attribute neutralHullRudderLengthM : Real = NumericalFunctions::max(candidate.length_m/2, -candidate.rudder_arm_fraction*candidate.length_m + rudderChordM/2) + NumericalFunctions::max(candidate.length_m/2, candidate.rudder_arm_fraction*candidate.length_m + rudderChordM/2);
        attribute qualified : Boolean = false;
    }
    part passage {
        attribute voyageEnergyMargin : Real = -1.2150509149932985e-07;
        attribute installationVolumeMargin : Real = 1.9629070633050338;
        attribute passageHours : Real = 35.72391247254426;
        attribute departureWh : Real = 246.83253862537308;
        attribute requiredWh : Real = 246.83255077588223;
        attribute batteryVolumeM3 : Real = 0.0017141148515650907;
        attribute equipmentVolumeM3 : Real = 0.00832431130030564;
        attribute availableVolumeM3 : Real = 0.029667496784921074;
    }
    dependency energyBasis from passage to BlueDogConceptCredibility::passagePolicy;
    part validation {
        attribute recoverySamples : Real = 24;
        attribute missingPitchRoots : Real = 0;
        attribute unstablePitchSamples : Real = 8;
        attribute adverseRollSamples : Real = 0;
        attribute constructionWorstDeflectionMargin : Real = -0.42857621765660214;
    }
    dependency recoveryBasis from validation to BlueDogRequirements::selfRighting;
    part mission {
        attribute scenarios : Real = 4;
        attribute virtualCompletions : Real = 1;
        attribute coverageStops : Real = 3;
        attribute minimumStoredWh : Real = 178.69126064390255;
        attribute protectedReserveWh : Real = 49.2;
    }
    dependency missionBasis from mission to BlueDogMissionSimulation::MissionOutcome;
}

// Generated by tools.boat_analysis.environment.climatology from frozen NOAA observations.
package BlueDogWindObservations {
    private import ScalarValues::*;
    part KDLS_warm : BlueDogWeather::StationSeason {
        attribute :>> station = "KDLS";
        attribute :>> season = "warm";
        attribute :>> expectedHours = 36720;
        attribute :>> observedHours = 36673;
        attribute :>> westHours = 16550;
        attribute :>> eastHours = 1808;
        attribute :>> lightHours = 7237;
        attribute :>> otherHours = 10131;
        attribute :>> unknownHours = 994;
        attribute :>> selectedWindows = 1821;
        attribute :>> windowsWithEast = 782;
        attribute :>> incompleteWindows = 4394;
    }
    part KDLS_winter : BlueDogWeather::StationSeason {
        attribute :>> station = "KDLS";
        attribute :>> season = "winter";
        attribute :>> expectedHours = 36312;
        attribute :>> observedHours = 36257;
        attribute :>> westHours = 6281;
        attribute :>> eastHours = 5857;
        attribute :>> lightHours = 19082;
        attribute :>> otherHours = 4569;
        attribute :>> unknownHours = 523;
        attribute :>> selectedWindows = 488;
        attribute :>> windowsWithEast = 429;
        attribute :>> incompleteWindows = 856;
    }
    part KDLS_transition : BlueDogWeather::StationSeason {
        attribute :>> station = "KDLS";
        attribute :>> season = "transition";
        attribute :>> expectedHours = 14640;
        attribute :>> observedHours = 14506;
        attribute :>> westHours = 4600;
        attribute :>> eastHours = 1646;
        attribute :>> lightHours = 5634;
        attribute :>> otherHours = 2364;
        attribute :>> unknownHours = 396;
        attribute :>> selectedWindows = 455;
        attribute :>> windowsWithEast = 353;
        attribute :>> incompleteWindows = 1132;
    }
    part KDLS_annual : BlueDogWeather::StationSeason {
        attribute :>> station = "KDLS";
        attribute :>> season = "annual";
        attribute :>> expectedHours = 87672;
        attribute :>> observedHours = 87436;
        attribute :>> westHours = 27431;
        attribute :>> eastHours = 9311;
        attribute :>> lightHours = 31953;
        attribute :>> otherHours = 17064;
        attribute :>> unknownHours = 1913;
        attribute :>> selectedWindows = 2764;
        attribute :>> windowsWithEast = 1564;
        attribute :>> incompleteWindows = 6382;
    }
    part KTTD_warm : BlueDogWeather::StationSeason {
        attribute :>> station = "KTTD";
        attribute :>> season = "warm";
        attribute :>> expectedHours = 36720;
        attribute :>> observedHours = 36665;
        attribute :>> westHours = 5548;
        attribute :>> eastHours = 2481;
        attribute :>> lightHours = 19675;
        attribute :>> otherHours = 3575;
        attribute :>> unknownHours = 5441;
        attribute :>> selectedWindows = 0;
        attribute :>> windowsWithEast = 0;
        attribute :>> incompleteWindows = 61;
    }
    part KTTD_winter : BlueDogWeather::StationSeason {
        attribute :>> station = "KTTD";
        attribute :>> season = "winter";
        attribute :>> expectedHours = 36312;
        attribute :>> observedHours = 36264;
        attribute :>> westHours = 2788;
        attribute :>> eastHours = 17328;
        attribute :>> lightHours = 10909;
        attribute :>> otherHours = 4602;
        attribute :>> unknownHours = 685;
        attribute :>> selectedWindows = 44;
        attribute :>> windowsWithEast = 41;
        attribute :>> incompleteWindows = 110;
    }
    part KTTD_transition : BlueDogWeather::StationSeason {
        attribute :>> station = "KTTD";
        attribute :>> season = "transition";
        attribute :>> expectedHours = 14640;
        attribute :>> observedHours = 14557;
        attribute :>> westHours = 1741;
        attribute :>> eastHours = 3481;
        attribute :>> lightHours = 6669;
        attribute :>> otherHours = 1988;
        attribute :>> unknownHours = 761;
        attribute :>> selectedWindows = 1;
        attribute :>> windowsWithEast = 0;
        attribute :>> incompleteWindows = 55;
    }
    part KTTD_annual : BlueDogWeather::StationSeason {
        attribute :>> station = "KTTD";
        attribute :>> season = "annual";
        attribute :>> expectedHours = 87672;
        attribute :>> observedHours = 87486;
        attribute :>> westHours = 10077;
        attribute :>> eastHours = 23290;
        attribute :>> lightHours = 37253;
        attribute :>> otherHours = 10165;
        attribute :>> unknownHours = 6887;
        attribute :>> selectedWindows = 45;
        attribute :>> windowsWithEast = 41;
        attribute :>> incompleteWindows = 226;
    }
}

// Generated by tools.boat_analysis.evidence.continuation.
package BlueDogSizingContinuation {
    private import ScalarValues::*;
    doc /* Coarse fixed-length feasibility only; no refined replay or physical qualification.
     * Hull length does not bound the full vessel footprint. Appendage geometry/model applicability,
     * chronological voyage energy and free-pitch dynamic recovery require further assessment. */
    part summary {
        attribute targetM : Real = 1.2;
        attribute smallestFeasibleM : Real = 1.2;
        attribute targetReached : Boolean = true;
        attribute qualified : Boolean = false;
    }
    part stage0 {
        attribute lengthM : Real = 2.0;
        attribute feasible : Boolean = true;
        attribute maximumResidual : Real = 7.145127156604758e-10;
        attribute minimumMargin : Real = -6.144964537213582e-10;
    }
    part stage1 {
        attribute lengthM : Real = 1.8;
        attribute feasible : Boolean = true;
        attribute maximumResidual : Real = 1.7880595226671403e-09;
        attribute minimumMargin : Real = -2.4811729580631603e-10;
    }
    part stage2 {
        attribute lengthM : Real = 1.6;
        attribute feasible : Boolean = true;
        attribute maximumResidual : Real = 4.353140070634254e-11;
        attribute minimumMargin : Real = -1.2223466683281003e-10;
    }
    part stage3 {
        attribute lengthM : Real = 1.4;
        attribute feasible : Boolean = true;
        attribute maximumResidual : Real = 2.0398403360033512e-05;
        attribute minimumMargin : Real = -1.2719669004734868e-06;
    }
    part stage4 {
        attribute lengthM : Real = 1.2;
        attribute feasible : Boolean = true;
        attribute maximumResidual : Real = 5.669689494665064e-05;
        attribute minimumMargin : Real = -4.6576547404919566e-05;
    }
    part candidate : MarineDesign::Design {
        attribute :>> length_m = 1.2;
        attribute :>> beam_m = 0.4344000000003233;
        attribute :>> bottom_depth_m = 0.04036604075998614;
        attribute :>> deck_height_m = 0.09446793532039352;
        attribute :>> sail_m2 = 0.8143812403943567;
        attribute :>> sail_AR = 2.0911634829244634;
        attribute :>> camber_scale = 1.1746000320485857;
        attribute :>> wing_thickness_scale = 1.1354616735897594;
        attribute :>> mast_fraction = 0.5120755733321997;
        attribute :>> mast_x_fraction = 0.029996841913039862;
        attribute :>> keel_m2 = 0.09591195537596085;
        attribute :>> keel_span_m = 0.5482450099155232;
        attribute :>> rudder_m2 = 0.09205295658604393;
        attribute :>> rudder_span_m = 0.08;
        attribute :>> rudder_arm_fraction = 0.5164052616843922;
        attribute :>> ballast_kg = 9.627177799148448;
        attribute :>> battery_Wh = 50.0;
        attribute :>> panel_m2 = 0.12068262127207481;
        attribute :>> wing_torque_Nm = 2.64136023561948;
        attribute :>> rudder_torque_Nm = 2.2438440735092002;
        attribute :>> hull_glass_kg_m2 = 0.4733356434802783;
        attribute :>> wing_glass_kg_m2 = 0.20000000000000012;
        attribute :>> keel_glass_kg_m2 = 4.067487321205885;
        attribute :>> rudder_glass_kg_m2 = 0.23249038742721195;
        attribute :>> hull_rib_pitch_m = 0.023470086332562604;
        attribute :>> foil_rib_pitch_m = 0.09251996467631225;
        attribute :>> battery_x_fraction = -0.3464999999999999;
        attribute :>> battery_z_fraction = 0.09533437422856002;
        attribute :>> hull_fullness_exponent = 1.5466427151983588;
    }
    dependency basis from candidate to BlueDogDesignDecisions::sizingBaseline;
    part assessment {
        attribute massKg : Real = 22.257347572176332;
        attribute westerlyHours : Real = 23.97409327486867;
        attribute rudderChordM : Real = candidate.rudder_m2 / candidate.rudder_span_m;
        attribute rudderAspectRatio : Real = candidate.rudder_span_m * candidate.rudder_span_m / candidate.rudder_m2;
        attribute neutralHullRudderLengthM : Real = NumericalFunctions::max(candidate.length_m/2, -candidate.rudder_arm_fraction*candidate.length_m + rudderChordM/2) + NumericalFunctions::max(candidate.length_m/2, candidate.rudder_arm_fraction*candidate.length_m + rudderChordM/2);
        attribute qualified : Boolean = false;
    }
}

// Generated by tools.publishing.srr from immutable run evidence.
package BlueDogSRRCurrent {
    private import ScalarValues::*;
    attribute evidenceManifest : String = "evidence/runs/2026-10-13-srr-readiness/manifest.json";
    part candidate {
        attribute batteryWh : Real = 440.0;
        attribute hullBeamM : Real = 0.26;
        attribute massKg : Real = 10.312830010265998;
        attribute westerlyPassageHours : Real = 33.86883519742054;
        attribute departureWh : Real = 316.8;
        attribute requiredWh : Real = 312.82633955094434;
        attribute energyHeadroomWh : Real = 3.9736604490556715;
        attribute balanced : Boolean = true;
        attribute staticScreensPass : Boolean = true;
        attribute physicallyQualified : Boolean = false;
        doc /* Retained concept with revised battery capacity and hull beam; nominal refined static replay.
         * Not a new optimum, hardware selection, dynamic recovery proof or mission qualification. */
    }
    part energyInputs {
        attribute sourceRevision : String = "b2aa167bc0a2cd7958246e20f70a227bc257bc39";
        attribute resinGlassRatio : Real = 1.0;
        attribute gearboxEfficiency : Real = 0.4;
        attribute motorEfficiency : Real = 0.8;
        attribute wingNoLoadW : Real = 1.0;
        attribute wingControllerW : Real = 0.1;
        attribute wingMotorHoldingW : Real = 0.0;
        attribute wingMoveFraction : Real = 0.02;
        attribute wingHoldingFraction : Real = 0.98;
        attribute rudderHoldingWPerNm : Real = 0.5;
        attribute rudderMoveFraction : Real = 0.05;
        attribute electronicsW : Real = 4.570486111111111;
        attribute solarResourceFactor : Real = 0.6;
        attribute batteryWhKg : Real = 140.0;
        attribute laminateKnockdown : Real = 1.0;
        attribute profileCd : Real = 0.04;
        attribute wingClLimit : Real = 0.9;
        attribute wingLiftScale : Real = 0.7;
        attribute wingDragScale : Real = 1.4;
        attribute wingRateRadS : Real = 0.25;
        attribute rudderRateRadS : Real = 0.6;
        attribute driveKgPerNm : Real = 0.15;
        attribute wingDriveBaseKg : Real = 0.2;
        attribute fixedEquipmentKg : Real = 2.5;
        attribute attachmentKg : Real = 0.6;
        attribute residuaryResistanceFactor : Real = 1.0;
        attribute viscousFormFactor : Real = 1.15;
        attribute foilClLimit : Real = 0.8;
        attribute foilEfficiency : Real = 0.7;
        attribute foilCd : Real = 0.012;
        attribute airNu : Real = 1.5e-05;
        attribute waterNu : Real = 1e-06;
        attribute waterDensity : Real = 1000.0;
        attribute airDensity : Real = 1.225;
        attribute ballastDensity : Real = 7800.0;
        attribute gravity : Real = 9.80665;
        attribute loadFactor : Real = 1.5;
        attribute assemblyLimitKg : Real = 15.0;
        attribute panelCoverage : Real = 0.6;
        attribute elevatedEquipmentKg : Real = 0.15;
        attribute elevatedEquipmentXFraction : Real = 0.0;
        attribute elevatedEquipmentAboveDeckM : Real = 0.3;
        attribute windBusW : Real = 0.07048611111111112;
        attribute durationMultiplier : Real = 1.25;
        attribute delayHours : Real = 6;
        attribute dischargeEfficiency : Real = 0.9;
        attribute usableFraction : Real = 0.8;
        attribute initialFraction : Real = 0.9;
        attribute selfDischargeW : Real = 0.02;
        attribute reserveWh : Real = 49.2;
    }
    part def EnergyCase {
        attribute label : String;
        attribute wingTorqueNm : Real;
        attribute rudderTorqueNm : Real;
        attribute recordedAverageW : Real;
        attribute recordedPeakW : Real;
    }
    part energyCase0 : EnergyCase {
        attribute :>> label = "5 m/s, windward, tack 1";
        attribute :>> wingTorqueNm = 0.09863444356620701;
        attribute :>> rudderTorqueNm = 0.05393485166632078;
        attribute :>> recordedAverageW = 4.869668885770823;
        attribute :>> recordedPeakW = 6.887995408896952;
    }
    part energyCase1 : EnergyCase {
        attribute :>> label = "5 m/s, windward, tack -1";
        attribute :>> wingTorqueNm = 0.09123004428899213;
        attribute :>> rudderTorqueNm = 0.05523090754102247;
        attribute :>> recordedAverageW = 4.870217420667901;
        attribute :>> recordedPeakW = 6.883182763867653;
    }
    part energyCase2 : EnergyCase {
        attribute :>> label = "5 m/s, leeward, tack 1";
        attribute :>> wingTorqueNm = 0.03252642271323138;
        attribute :>> rudderTorqueNm = 0.030308416903813272;
        attribute :>> recordedAverageW = 4.85652740012921;
        attribute :>> recordedPeakW = 6.818628691533684;
    }
    part energyCase3 : EnergyCase {
        attribute :>> label = "5 m/s, leeward, tack -1";
        attribute :>> wingTorqueNm = 0.05496520460434538;
        attribute :>> rudderTorqueNm = 0.029163488989072714;
        attribute :>> recordedAverageW = 4.856291230539954;
        attribute :>> recordedPeakW = 6.835300293950061;
    }
    part energyCase4 : EnergyCase {
        attribute :>> label = "8 m/s, windward, tack 1";
        attribute :>> wingTorqueNm = 0.5517728761051918;
        attribute :>> rudderTorqueNm = 0.07956789220334846;
        attribute :>> recordedAverageW = 4.889886107054471;
        attribute :>> recordedPeakW = 7.261234589720804;
    }
    part energyCase5 : EnergyCase {
        attribute :>> label = "8 m/s, windward, tack -1";
        attribute :>> wingTorqueNm = 0.5517728761052052;
        attribute :>> rudderTorqueNm = 0.0810173703045101;
        attribute :>> recordedAverageW = 4.890628964581317;
        attribute :>> recordedPeakW = 7.262321698296685;
    }
    part energyCase6 : EnergyCase {
        attribute :>> label = "8 m/s, leeward, tack 1";
        attribute :>> wingTorqueNm = 0.05571530282314596;
        attribute :>> rudderTorqueNm = 0.053792082393333496;
        attribute :>> recordedAverageW = 4.8689251049443065;
        attribute :>> recordedPeakW = 6.854357753236695;
    }
    part energyCase7 : EnergyCase {
        attribute :>> label = "8 m/s, leeward, tack -1";
        attribute :>> wingTorqueNm = 0.11945081411444261;
        attribute :>> rudderTorqueNm = 0.050200672313092345;
        attribute :>> recordedAverageW = 4.868080374642109;
        attribute :>> recordedPeakW = 6.901457563872839;
    }
    alias energyGoverningCase for energyCase5;
    alias peakGoverningCase for energyCase5;
    dependency energyBasis from candidate to BlueDogConceptCredibility::passagePolicy;
    dependency recoveryBasis from candidate to BlueDogRequirements::lowEnergyRecovery;
}

// Generated by tools.publishing.frontier; edit the source analysis, not these values.
package BlueDogSRRFrontier {
    private import ScalarValues::*;
    doc /* Local coarse monohull search, not physical qualification or a calibrated mission probability.
     * Unresolved searches do not prove infeasibility. The replay applies to the retained seed, not every alternative. */
    attribute evidenceManifest : String = "evidence/runs/2026-10-13-srr-frontier/manifest.json";
    attribute pointNames : String [*] ordered nonunique = ("BlueDogSRRFrontier::point0", "BlueDogSRRFrontier::point1", "BlueDogSRRFrontier::point2", "BlueDogSRRFrontier::point3", "BlueDogSRRFrontier::point4", "BlueDogSRRFrontier::point5");
    part point0 {
        attribute capM : Real = 1.2;
        attribute optimizationObjective : String = "massKg";
        attribute feasible : Boolean = true;
        attribute solverConverged : Boolean = false;
        attribute overallLengthM : Real = 1.19999999999918;
        attribute massKg : Real = 10.251979623823363;
        attribute conditionalPassageHours : Real = 33.69993514266723;
        attribute maxEquilibriumResidual : Real = 3.0056176298520753e-05;
        attribute minimumMargin : Real = -2.8849930515093548e-05;
    }
    part point1 {
        attribute capM : Real = 1.2;
        attribute optimizationObjective : String = "conditionalPassageHours";
        attribute feasible : Boolean = true;
        attribute solverConverged : Boolean = false;
        attribute overallLengthM : Real = 1.19999999999912;
        attribute massKg : Real = 10.252018537728546;
        attribute conditionalPassageHours : Real = 33.660701261300844;
        attribute maxEquilibriumResidual : Real = 3.455479958631713e-05;
        attribute minimumMargin : Real = -3.05103158257225e-05;
    }
    part point2 {
        attribute capM : Real = 1.0;
        attribute optimizationObjective : String = "massKg";
        attribute feasible : Boolean = false;
        attribute solverConverged : Boolean = false;
        attribute overallLengthM : Real = 0.99999999999978;
        attribute massKg : Real = 10.552607614662792;
        attribute conditionalPassageHours : Real = 39.54397530339136;
        attribute maxEquilibriumResidual : Real = 0.013272813945328643;
        attribute minimumMargin : Real = -0.07408293173826053;
    }
    part point3 {
        attribute capM : Real = 1.0;
        attribute optimizationObjective : String = "conditionalPassageHours";
        attribute feasible : Boolean = false;
        attribute solverConverged : Boolean = false;
        attribute overallLengthM : Real = 1.08287401940678;
        attribute massKg : Real = 13.915531549193123;
        attribute conditionalPassageHours : Real = 29.093649494420255;
        attribute maxEquilibriumResidual : Real = 0.06851245536571367;
        attribute minimumMargin : Real = -0.3060228212366165;
    }
    part point4 {
        attribute capM : Real = 0.8;
        attribute optimizationObjective : String = "massKg";
        attribute feasible : Boolean = false;
        attribute solverConverged : Boolean = false;
        attribute overallLengthM : Real = 0.93547442072642;
        attribute massKg : Real = 11.359587063925092;
        attribute conditionalPassageHours : Real = 52.414615902711915;
        attribute maxEquilibriumResidual : Real = 0.14332133293069468;
        attribute minimumMargin : Real = -0.559342149485484;
    }
    part point5 {
        attribute capM : Real = 0.8;
        attribute optimizationObjective : String = "conditionalPassageHours";
        attribute feasible : Boolean = false;
        attribute solverConverged : Boolean = false;
        attribute overallLengthM : Real = 0.91345640313512;
        attribute massKg : Real = 10.91774017210988;
        attribute conditionalPassageHours : Real = 45.921314701972314;
        attribute maxEquilibriumResidual : Real = 0.09582011825541861;
        attribute minimumMargin : Real = -0.4289869070673995;
    }
    part retainedSeedReplay {
        attribute massKg : Real = 10.252018537728546;
        attribute westerlyHours : Real = 33.74174149441574;
        attribute numericallyBalanced : Boolean = true;
        attribute voyageEnergyMargin : Real = -0.0055600033951458275;
        attribute sampledRightingPass : Boolean = true;
        attribute profileScreensPass : Boolean = false;
        attribute qualified : Boolean = false;
    }
}

package MarineActuation {
    private import ScalarValues::*;

    calc def MastTorque {
        in densityKgM3 : Real;
        in apparentWindMS : Real;
        in sailAreaM2 : Real;
        in chordM : Real;
        in momentCoefficientAtMast : Real;
        in bearingFrictionNm : Real;
        return torqueNm : Real;
        0.5*densityKgM3*apparentWindMS*apparentWindMS*sailAreaM2*chordM*RealFunctions::abs(momentCoefficientAtMast)+bearingFrictionNm
    }
    calc def DrivePower {
        doc /* Preconditions: efficiencies in (0,1], nonnegative powers and duty
         * fractions; moving plus holding fraction at most one. The external
         * sizing adapter must reject inputs outside these domains. */
        in shaftTorqueNm : Real;
        in shaftSpeedRadS : Real;
        in motorEfficiency : Real;
        in gearboxEfficiency : Real;
        in motorNoLoadW : Real;
        in controllerW : Real;
        in motorHoldingW : Real;
        in moveFraction : Real;
        in holdingFraction : Real;
        attribute movingW : Real = controllerW+motorNoLoadW+RealFunctions::abs(shaftTorqueNm*shaftSpeedRadS)/(motorEfficiency*gearboxEfficiency);
        attribute holdingW : Real = controllerW+motorHoldingW;
        return powersW : Real [3] ordered nonunique;
        (moveFraction*movingW+holdingFraction*holdingW+(1-moveFraction-holdingFraction)*controllerW,
            NumericalFunctions::max(movingW,holdingW),movingW)
    }
    calc def DailyEnergy {
        in averagePowerW : Real;
        in durationHours : Real;
        return energyWh : Real;
        averagePowerW*durationHours
    }
}

package MarineEnergy {
    private import ScalarValues::*;
    private import ISQ::*;
    private import SI::*;
    part def ElectricalLoad {
        attribute label : String;
        attribute activePower : PowerValue;
        attribute idlePower : PowerValue;
        attribute activeFraction : Real;
        attribute conversionEfficiency : Real;
        attribute uncertaintyFactor : Real;
        attribute averagePower : PowerValue =
            (idlePower + (activePower - idlePower) * activeFraction) * uncertaintyFactor / conversionEfficiency;
        attribute peakPower : PowerValue = activePower * uncertaintyFactor / conversionEfficiency;
        attribute valid : Boolean = activePower >= idlePower and idlePower >= 0 [W] and
        activeFraction >= 0 and activeFraction <= 1 and
        conversionEfficiency > 0 and conversionEfficiency <= 1 and uncertaintyFactor >= 1;
    }
    part def LoadBudget {
        part loads : ElectricalLoad [1..*] ordered;
        attribute averagePower : PowerValue = NumericalFunctions::sum(loads.averagePower);
        attribute peakPower : PowerValue = NumericalFunctions::sum(loads.peakPower);
        attribute valid : Boolean = SequenceFunctions::size(loads) > 0 and
        loads->ControlFunctions::forAll { in load : ElectricalLoad; load.valid };
    }
    part def Battery {
        attribute nominalEnergy : EnergyValue;
        attribute usableFraction : Real;
        attribute capacity : EnergyValue = nominalEnergy * usableFraction;
        attribute chargeEfficiency : Real;
        attribute dischargeEfficiency : Real;
        attribute maxChargePower : PowerValue;
        attribute selfDischargePower : PowerValue;
        attribute maxDischargePower : PowerValue;
        attribute valid : Boolean = nominalEnergy > 0 [J] and usableFraction > 0 and usableFraction <= 1 and
        chargeEfficiency > 0 and chargeEfficiency <= 1 and
        dischargeEfficiency > 0 and dischargeEfficiency <= 1 and
        maxChargePower >= 0 [W] and maxDischargePower > 0 [W] and selfDischargePower >= 0 [W];
    }
    part def Interval {
        ref part budget : LoadBudget;
        attribute duration : TimeValue;
        attribute harvestEnabled : Boolean;
        attribute rawHarvestPower : PowerValue;
        attribute harvestEfficiency : Real;
        attribute busHarvestPower : PowerValue = if harvestEnabled ? rawHarvestPower * harvestEfficiency else 0 [W];
        attribute netBusPower : PowerValue = busHarvestPower - budget.averagePower;
        attribute valid : Boolean = duration > 0 [s] and rawHarvestPower >= 0 [W] and
        harvestEfficiency > 0 and harvestEfficiency <= 1 and budget.valid;
    }
    calc def StorageRate {
        in interval : Interval;
        in battery : Battery;
        return rate : PowerValue;
        if interval.netBusPower >= 0 [W] ?
            NumericalFunctions::min(interval.netBusPower * battery.chargeEfficiency / (1 [W]), battery.maxChargePower / (1 [W])) * 1 [W] - battery.selfDischargePower
        else interval.netBusPower / battery.dischargeEfficiency - battery.selfDischargePower
    }
    analysis def BudgetRollup {
        subject budget : LoadBudget;
        assert constraint validInputs { budget.valid }
        out attribute labels : String [*] ordered nonunique = budget.loads.label;
        out attribute averageContributions : PowerValue [*] ordered nonunique = budget.loads.averagePower;
        out attribute peakContributions : PowerValue [*] ordered nonunique = budget.loads.peakPower;
        out attribute coincidentPeak : PowerValue = budget.peakPower;
        return averageDemand : PowerValue = budget.averagePower;
    }
}

package MarineAppendages {
    private import ScalarValues::*;
    calc def GeometryMargins {
        in d : Real [29] ordered nonunique;
        in minimumAspectRatio : Real;
        in clearanceM : Real;
        doc /* Rectangular underwater foils centered at x=0 (keel) and
         * x=-arm*length (rudder), with a center-chord rudder stock. The swept
         * disk bounds all steering angles, including thickness for the current
         * elliptical 12-percent section. This is a planform screen, not a
         * bearing, bracket, hull-intersection or bulb-clearance assessment. */
        attribute keelChord : Real = d#(11)/d#(12);
        attribute rudderChord : Real = d#(13)/d#(14);
        attribute keelAspectMargin : Real = d#(12)*d#(12)/d#(11)/minimumAspectRatio-1;
        attribute rudderAspectMargin : Real = d#(14)*d#(14)/d#(13)/minimumAspectRatio-1;
        attribute keelRootMargin : Real = 1-keelChord/d#(1);
        attribute rudderStockMargin : Real = 1-2*d#(15);
        attribute sweptSeparationMargin : Real = (d#(15)*d#(1)-(keelChord+rudderChord)/2-clearanceM)/d#(1);
        return result : Real [5] ordered nonunique;
        (keelAspectMargin,rudderAspectMargin,keelRootMargin,rudderStockMargin,sweptSeparationMargin)
    }
}

package MarineConcept {
    private import ScalarValues::*;
    calc def Evaluate {
        in d : Real [29] ordered nonunique;
        in m : Real [21] ordered nonunique;
        in g : Real [60] ordered nonunique;
        in q : Real [24] ordered nonunique;
        in policy : Real [5] ordered nonunique;
        in voyage : Real [2] ordered nonunique;
        doc /* SI numerical boundary: voyage = conditional hours, maximum bus W.
         * Policy = duration multiplier, delay hours, installed battery Wh/m3,
         * equipment installed kg/m3, usable hull-volume fraction.
         * No harvest credit: a finite-passage screening scenario, not perpetual
         * energy balance or a completion deadline. Volume is necessary but not
         * sufficient for local fit, access, watertightness or manufacturing. */
        attribute passageHours : Real = voyage#(1)*policy#(1)+policy#(2);
        attribute departureWh : Real = d#(17)*q#(16)*q#(17);
        attribute demandWh : Real = passageHours*(voyage#(2)/q#(15)+q#(20));
        attribute requiredWh : Real = demandWh+q#(23);
        attribute voyageEnergyMargin : Real = (departureWh-requiredWh)/100;
        attribute batteryVolumeM3 : Real = d#(17)/policy#(3);
        attribute equipmentVolumeM3 : Real = (m#(8)+m#(9)+m#(10))/policy#(4);
        attribute availableVolumeM3 : Real = (g#(5)-m#(14))*policy#(5);
        attribute installationVolumeMargin : Real = (availableVolumeM3-batteryVolumeM3-equipmentVolumeM3)/0.01;
        return result : Real [8] ordered nonunique;
        (voyageEnergyMargin,installationVolumeMargin,passageHours,departureWh,requiredWh,batteryVolumeM3,equipmentVolumeM3,availableVolumeM3)
    }
}

package MarineCourse {
    private import ScalarValues::*;
    calc def TackAverage {
        in a : Real; in b : Real; in lateralA : Real; in lateralB : Real;
        return vmg : Real;
        (a*RealFunctions::abs(lateralB)+b*RealFunctions::abs(lateralA))/(RealFunctions::abs(lateralA)+RealFunctions::abs(lateralB))
    }
    calc def Route {
        doc /* Policy element 6 scales positive-progress residuals; it is not a minimum ground-speed requirement. */
        in water : Real [8] ordered nonunique;
        in states : Real [48] ordered nonunique;
        in policy : Real [7] ordered nonunique;
        doc /* Cases ordered by wind 5 then 8 m/s, windward then leeward, tack + then -.
         * Each state contains speed, heading, incidence, leeway, rudder and heel.
         * Tack times cancel crosswind displacement. Equal time fractions per wind
         * and 0.5/1.0 m/s downstream current are illustrative, not weather evidence.
         * This is conditional on one persistent direction, not a probability
         * distribution. Neither station hourly fractions nor scenario counts
         * justify treating these equal speed weights as climatology.
         * policy#5 is an optional duration budget in hours; zero disables that screen.
         * policy#7 is 1 for easterly (upstream windward), 0 for westerly. */
        attribute cross0 : Real = states#(1)*TrigFunctions::sin(TrigFunctions::rad(states#(2)+states#(4)));
        attribute cross1 : Real = states#(7)*TrigFunctions::sin(TrigFunctions::rad(states#(8)+states#(10)));
        attribute cross2 : Real = states#(13)*TrigFunctions::sin(TrigFunctions::rad(states#(14)+states#(16)));
        attribute cross3 : Real = states#(19)*TrigFunctions::sin(TrigFunctions::rad(states#(20)+states#(22)));
        attribute cross4 : Real = states#(25)*TrigFunctions::sin(TrigFunctions::rad(states#(26)+states#(28)));
        attribute cross5 : Real = states#(31)*TrigFunctions::sin(TrigFunctions::rad(states#(32)+states#(34)));
        attribute cross6 : Real = states#(37)*TrigFunctions::sin(TrigFunctions::rad(states#(38)+states#(40)));
        attribute cross7 : Real = states#(43)*TrigFunctions::sin(TrigFunctions::rad(states#(44)+states#(46)));
        attribute vmg0 : Real = TackAverage(water#(1),water#(2),cross0,cross1);
        attribute vmg1 : Real = TackAverage(water#(3),water#(4),cross2,cross3);
        attribute vmg2 : Real = TackAverage(water#(5),water#(6),cross4,cross5);
        attribute vmg3 : Real = TackAverage(water#(7),water#(8),cross6,cross7);
        attribute windwardMean : Real = (vmg0+vmg2)/2;
        attribute leewardMean : Real = (vmg1+vmg3)/2;
        attribute downstream : Real = policy#(1)*(if policy#(7)>0.5 ? leewardMean else windwardMean)+(policy#(2)+policy#(3))/2;
        attribute upstream : Real = policy#(1)*(if policy#(7)>0.5 ? windwardMean else leewardMean)-(policy#(2)+policy#(3))/2;
        attribute duration : Real = if downstream>0 and upstream>0 ? policy#(4)/3600*(1/downstream+1/upstream) else 1000000.0;
        attribute downstreamProgress : Real = downstream/policy#(6);
        attribute upstreamProgress : Real = upstream/policy#(6);
        attribute durationMargin : Real = if policy#(5)>0 ? 1-duration/policy#(5) else 1.0;
        return result : Real [6] ordered nonunique;
        (downstreamProgress,upstreamProgress,durationMargin,downstream,upstream,duration)
    }
}

package MarineDesign {
    private import ScalarValues::*;
    doc /* Named SI numerical contract for a hull, rotating wing, keel and rudder.
     * Names carry units: metres, square metres, kg, Wh, Nm, kg/m2 and rad/s.
     * Fractions and scales are dimensionless. Arrays exist only at the compiled
     * numerical boundary; application configurations own values and evidence. */
    part def Design {
        attribute length_m : Real;
        attribute beam_m : Real;
        attribute bottom_depth_m : Real;
        attribute deck_height_m : Real;
        attribute sail_m2 : Real;
        attribute sail_AR : Real;
        attribute camber_scale : Real;
        attribute wing_thickness_scale : Real;
        attribute mast_fraction : Real;
        attribute mast_x_fraction : Real;
        attribute keel_m2 : Real;
        attribute keel_span_m : Real;
        attribute rudder_m2 : Real;
        attribute rudder_span_m : Real;
        attribute rudder_arm_fraction : Real;
        attribute ballast_kg : Real;
        attribute battery_Wh : Real;
        attribute panel_m2 : Real;
        attribute wing_torque_Nm : Real;
        attribute rudder_torque_Nm : Real;
        attribute hull_glass_kg_m2 : Real;
        attribute wing_glass_kg_m2 : Real;
        attribute keel_glass_kg_m2 : Real;
        attribute rudder_glass_kg_m2 : Real;
        attribute hull_rib_pitch_m : Real;
        attribute foil_rib_pitch_m : Real;
        attribute battery_x_fraction : Real;
        attribute battery_z_fraction : Real;
        attribute hull_fullness_exponent : Real;
    }
    calc def DesignVector {
        in value : Design;
        return vector : Real [29] ordered nonunique;
        (value.length_m, value.beam_m, value.bottom_depth_m, value.deck_height_m, value.sail_m2, value.sail_AR, value.camber_scale, value.wing_thickness_scale, value.mast_fraction, value.mast_x_fraction, value.keel_m2, value.keel_span_m, value.rudder_m2, value.rudder_span_m, value.rudder_arm_fraction, value.ballast_kg, value.battery_Wh, value.panel_m2, value.wing_torque_Nm, value.rudder_torque_Nm, value.hull_glass_kg_m2, value.wing_glass_kg_m2, value.keel_glass_kg_m2, value.rudder_glass_kg_m2, value.hull_rib_pitch_m, value.foil_rib_pitch_m, value.battery_x_fraction, value.battery_z_fraction, value.hull_fullness_exponent)
    }
    part def Parameters {
        attribute resinGlassRatio : Real;
        attribute gearboxEfficiency : Real;
        attribute motorEfficiency : Real;
        attribute wingNoLoadW : Real;
        attribute wingControllerW : Real;
        attribute wingMotorHoldingW : Real;
        attribute wingMoveFraction : Real;
        attribute wingHoldingFraction : Real;
        attribute rudderHoldingWPerNm : Real;
        attribute rudderMoveFraction : Real;
        attribute electronicsW : Real;
        attribute solarResourceFactor : Real;
        attribute batteryWhKg : Real;
        attribute laminateKnockdown : Real;
        attribute profileCd : Real;
        attribute wingClLimit : Real;
        attribute wingLiftScale : Real;
        attribute wingDragScale : Real;
        attribute wingRateRadS : Real;
        attribute rudderRateRadS : Real;
        attribute driveKgPerNm : Real;
        attribute wingDriveBaseKg : Real;
        attribute fixedEquipmentKg : Real;
        attribute attachmentKg : Real;
        attribute residuaryResistanceFactor : Real;
        attribute viscousFormFactor : Real;
        attribute foilClLimit : Real;
        attribute foilEfficiency : Real;
        attribute foilCd : Real;
        attribute airNu : Real;
        attribute waterNu : Real;
        attribute waterDensity : Real;
        attribute airDensity : Real;
        attribute ballastDensity : Real;
        attribute gravity : Real;
        attribute loadFactor : Real;
        attribute assemblyLimitKg : Real;
        attribute panelCoverage : Real;
        attribute elevatedEquipmentKg : Real default = 0;
        attribute elevatedEquipmentXFraction : Real default = 0;
        attribute elevatedEquipmentAboveDeckM : Real default = 0;
    }
    calc def ParametersVector {
        in value : Parameters;
        return vector : Real [41] ordered nonunique;
        (value.resinGlassRatio, value.gearboxEfficiency, value.motorEfficiency, value.wingNoLoadW, value.wingControllerW, value.wingMotorHoldingW, value.wingMoveFraction, value.wingHoldingFraction, value.rudderHoldingWPerNm, value.rudderMoveFraction, value.electronicsW, value.solarResourceFactor, value.batteryWhKg, value.laminateKnockdown, value.profileCd, value.wingClLimit, value.wingLiftScale, value.wingDragScale, value.wingRateRadS, value.rudderRateRadS, value.driveKgPerNm, value.wingDriveBaseKg, value.fixedEquipmentKg, value.attachmentKg, value.residuaryResistanceFactor, value.viscousFormFactor, value.foilClLimit, value.foilEfficiency, value.foilCd, value.airNu, value.waterNu, value.waterDensity, value.airDensity, value.ballastDensity, value.gravity, value.loadFactor, value.assemblyLimitKg, value.panelCoverage, value.elevatedEquipmentKg, value.elevatedEquipmentXFraction, value.elevatedEquipmentAboveDeckM)
    }
    part def OperatingState {
        doc /* Named numerical boundary. Declaration order defines the native vector ABI. */
        attribute windSpeed_m_s : Real;
        attribute windward : Real;
        attribute foulingMultiplier : Real;
        attribute speed_m_s : Real;
        attribute windFrom_deg : Real;
        attribute incidence_deg : Real;
        attribute leeway_deg : Real;
        attribute rudder_deg : Real;
        attribute heel_deg : Real;
    }
    part def AeroCoefficients {
        doc /* Named numerical boundary. Declaration order defines the native vector ABI. */
        attribute liftCoefficient : Real;
        attribute dragCoefficient : Real;
        attribute midchordMomentCoefficient : Real;
    }
    part def HydroState {
        doc /* Named numerical boundary. Declaration order defines the native vector ABI. */
        attribute waterline_m : Real;
        attribute righting_Nm : Real;
        attribute wettedHullArea_m2 : Real;
        attribute waterlineLength_m : Real;
        attribute waterlineBeam_m : Real;
        attribute canoeDraft_m : Real;
        attribute displacementVolume_m3 : Real;
        attribute waterplaneArea_m2 : Real;
        attribute lcbAftFP_m : Real;
        attribute lcfAftFP_m : Real;
        attribute prismaticCoefficient : Real;
        attribute midshipCoefficient : Real;
    }
    part def AppendageLoads {
        doc /* Named numerical boundary. Declaration order defines the native vector ABI. */
        attribute wingResultant : Real;
        attribute keelResultant : Real;
        attribute rudderResultant : Real;
    }
    part def Passage {
        doc /* Named numerical boundary. Declaration order defines the native vector ABI. */
        attribute duration_h : Real;
        attribute averagePower_W : Real;
    }
    part def MassProperties {
        doc /* Named numerical boundary. Declaration order defines the native vector ABI. */
        attribute totalMass : Real;
        attribute hullMass : Real;
        attribute wingMass : Real;
        attribute keelMass : Real;
        attribute rudderMass : Real;
        attribute batteryMass : Real;
        attribute panelMass : Real;
        attribute wingDriveMass : Real;
        attribute rudderDriveMass : Real;
        attribute equipmentMass : Real;
        attribute cgX : Real;
        attribute cgY : Real;
        attribute cgZ : Real;
        attribute hullMaterialVolume : Real;
        attribute wingMaterialVolume : Real;
        attribute keelMaterialVolume : Real;
        attribute rudderMaterialVolume : Real;
        attribute hullLaminateThickness : Real;
        attribute wingLaminateThickness : Real;
        attribute keelLaminateThickness : Real;
        attribute rudderLaminateThickness : Real;
    }
}

package MarineResistance {
    private import ScalarValues::*;
    doc /* Keuning and Katgert (2008), A Bare Hull Resistance Prediction Method
     * Derived from the Results of the Delft Systematic Yacht Hull Series Extended
     * to Higher Speeds, equation 1.7 and tables 1-2.
     * Source: https://www.scribd.com/document/346520042/Keuning-2008-pdf
     * Untrimmed, upright, bare-hull residuary resistance only. Not a total-drag,
     * heeled-hull, sail-induced trim, roughness or wave-added-resistance model.
     * Table-1 coordinate bounds are necessary screening limits, not evidence that
     * every combination inside their rectangular envelope is supported.
     * Beyond Fn 0.60 fewer hulls were tested; this implementation's admissible
     * domain stops at 0.60 pending speed-dependent coverage evidence. */
    calc def Coefficients {
        in fn : Real;
        attribute a0 : Real = if fn <= 0.20 ? -0.0005 + (fn - 0.15) / 0.05 * (-0.0003 - (-0.0005)) else if fn <= 0.25 ? -0.0003 + (fn - 0.20) / 0.05 * (-0.0002 - (-0.0003)) else if fn <= 0.30 ? -0.0002 + (fn - 0.25) / 0.05 * (-0.0009 - (-0.0002)) else if fn <= 0.35 ? -0.0009 + (fn - 0.30) / 0.05 * (-0.0026 - (-0.0009)) else if fn <= 0.40 ? -0.0026 + (fn - 0.35) / 0.05 * (-0.0064 - (-0.0026)) else if fn <= 0.45 ? -0.0064 + (fn - 0.40) / 0.05 * (-0.0218 - (-0.0064)) else if fn <= 0.50 ? -0.0218 + (fn - 0.45) / 0.05 * (-0.0388 - (-0.0218)) else if fn <= 0.55 ? -0.0388 + (fn - 0.50) / 0.05 * (-0.0347 - (-0.0388)) else if fn <= 0.60 ? -0.0347 + (fn - 0.55) / 0.05 * (-0.0361 - (-0.0347)) else if fn <= 0.65 ? -0.0361 + (fn - 0.60) / 0.05 * (0.0008 - (-0.0361)) else if fn <= 0.70 ? 0.0008 + (fn - 0.65) / 0.05 * (0.0108 - (0.0008)) else if fn <= 0.75 ? 0.0108 + (fn - 0.70) / 0.05 * (0.1023 - (0.0108)) else 0.1023;
        attribute a1 : Real = if fn <= 0.20 ? 0.0023 + (fn - 0.15) / 0.05 * (0.0059 - (0.0023)) else if fn <= 0.25 ? 0.0059 + (fn - 0.20) / 0.05 * (-0.0156 - (0.0059)) else if fn <= 0.30 ? -0.0156 + (fn - 0.25) / 0.05 * (0.0016 - (-0.0156)) else if fn <= 0.35 ? 0.0016 + (fn - 0.30) / 0.05 * (-0.0567 - (0.0016)) else if fn <= 0.40 ? -0.0567 + (fn - 0.35) / 0.05 * (-0.4034 - (-0.0567)) else if fn <= 0.45 ? -0.4034 + (fn - 0.40) / 0.05 * (-0.5261 - (-0.4034)) else if fn <= 0.50 ? -0.5261 + (fn - 0.45) / 0.05 * (-0.5986 - (-0.5261)) else if fn <= 0.55 ? -0.5986 + (fn - 0.50) / 0.05 * (-0.4764 - (-0.5986)) else if fn <= 0.60 ? -0.4764 + (fn - 0.55) / 0.05 * (0.0037 - (-0.4764)) else if fn <= 0.65 ? 0.0037 + (fn - 0.60) / 0.05 * (0.3728 - (0.0037)) else if fn <= 0.70 ? 0.3728 + (fn - 0.65) / 0.05 * (-0.1238 - (0.3728)) else if fn <= 0.75 ? -0.1238 + (fn - 0.70) / 0.05 * (0.7726 - (-0.1238)) else 0.7726;
        attribute a2 : Real = if fn <= 0.20 ? -0.0086 + (fn - 0.15) / 0.05 * (-0.0064 - (-0.0086)) else if fn <= 0.25 ? -0.0064 + (fn - 0.20) / 0.05 * (0.0031 - (-0.0064)) else if fn <= 0.30 ? 0.0031 + (fn - 0.25) / 0.05 * (0.0337 - (0.0031)) else if fn <= 0.35 ? 0.0337 + (fn - 0.30) / 0.05 * (0.0446 - (0.0337)) else if fn <= 0.40 ? 0.0446 + (fn - 0.35) / 0.05 * (-0.125 - (0.0446)) else if fn <= 0.45 ? -0.125 + (fn - 0.40) / 0.05 * (-0.2945 - (-0.125)) else if fn <= 0.50 ? -0.2945 + (fn - 0.45) / 0.05 * (-0.3038 - (-0.2945)) else if fn <= 0.55 ? -0.3038 + (fn - 0.50) / 0.05 * (-0.2361 - (-0.3038)) else if fn <= 0.60 ? -0.2361 + (fn - 0.55) / 0.05 * (-0.296 - (-0.2361)) else if fn <= 0.65 ? -0.296 + (fn - 0.60) / 0.05 * (-0.3667 - (-0.296)) else if fn <= 0.70 ? -0.3667 + (fn - 0.65) / 0.05 * (-0.2026 - (-0.3667)) else if fn <= 0.75 ? -0.2026 + (fn - 0.70) / 0.05 * (0.504 - (-0.2026)) else 0.504;
        attribute a3 : Real = if fn <= 0.20 ? -0.0015 + (fn - 0.15) / 0.05 * (0.007 - (-0.0015)) else if fn <= 0.25 ? 0.007 + (fn - 0.20) / 0.05 * (-0.0021 - (0.007)) else if fn <= 0.30 ? -0.0021 + (fn - 0.25) / 0.05 * (-0.0285 - (-0.0021)) else if fn <= 0.35 ? -0.0285 + (fn - 0.30) / 0.05 * (-0.1091 - (-0.0285)) else if fn <= 0.40 ? -0.1091 + (fn - 0.35) / 0.05 * (0.0273 - (-0.1091)) else if fn <= 0.45 ? 0.0273 + (fn - 0.40) / 0.05 * (0.2485 - (0.0273)) else if fn <= 0.50 ? 0.2485 + (fn - 0.45) / 0.05 * (0.6033 - (0.2485)) else if fn <= 0.55 ? 0.6033 + (fn - 0.50) / 0.05 * (0.8726 - (0.6033)) else if fn <= 0.60 ? 0.8726 + (fn - 0.55) / 0.05 * (0.9661 - (0.8726)) else if fn <= 0.65 ? 0.9661 + (fn - 0.60) / 0.05 * (1.3957 - (0.9661)) else if fn <= 0.70 ? 1.3957 + (fn - 0.65) / 0.05 * (1.1282 - (1.3957)) else if fn <= 0.75 ? 1.1282 + (fn - 0.70) / 0.05 * (1.7867 - (1.1282)) else 1.7867;
        attribute a4 : Real = if fn <= 0.20 ? 0.0061 + (fn - 0.15) / 0.05 * (0.0014 - (0.0061)) else if fn <= 0.25 ? 0.0014 + (fn - 0.20) / 0.05 * (-0.007 - (0.0014)) else if fn <= 0.30 ? -0.007 + (fn - 0.25) / 0.05 * (-0.0367 - (-0.007)) else if fn <= 0.35 ? -0.0367 + (fn - 0.30) / 0.05 * (-0.0707 - (-0.0367)) else if fn <= 0.40 ? -0.0707 + (fn - 0.35) / 0.05 * (-0.1341 - (-0.0707)) else if fn <= 0.45 ? -0.1341 + (fn - 0.40) / 0.05 * (-0.2428 - (-0.1341)) else if fn <= 0.50 ? -0.2428 + (fn - 0.45) / 0.05 * (-0.043 - (-0.2428)) else if fn <= 0.55 ? -0.043 + (fn - 0.50) / 0.05 * (0.4219 - (-0.043)) else if fn <= 0.60 ? 0.4219 + (fn - 0.55) / 0.05 * (0.6123 - (0.4219)) else if fn <= 0.65 ? 0.6123 + (fn - 0.60) / 0.05 * (1.0343 - (0.6123)) else if fn <= 0.70 ? 1.0343 + (fn - 0.65) / 0.05 * (1.1836 - (1.0343)) else if fn <= 0.75 ? 1.1836 + (fn - 0.70) / 0.05 * (2.1934 - (1.1836)) else 2.1934;
        attribute a5 : Real = if fn <= 0.20 ? 0.001 + (fn - 0.15) / 0.05 * (0.0013 - (0.001)) else if fn <= 0.25 ? 0.0013 + (fn - 0.20) / 0.05 * (0.0148 - (0.0013)) else if fn <= 0.30 ? 0.0148 + (fn - 0.25) / 0.05 * (0.0218 - (0.0148)) else if fn <= 0.35 ? 0.0218 + (fn - 0.30) / 0.05 * (0.0914 - (0.0218)) else if fn <= 0.40 ? 0.0914 + (fn - 0.35) / 0.05 * (0.3578 - (0.0914)) else if fn <= 0.45 ? 0.3578 + (fn - 0.40) / 0.05 * (0.6293 - (0.3578)) else if fn <= 0.50 ? 0.6293 + (fn - 0.45) / 0.05 * (0.8332 - (0.6293)) else if fn <= 0.55 ? 0.8332 + (fn - 0.50) / 0.05 * (0.899 - (0.8332)) else if fn <= 0.60 ? 0.899 + (fn - 0.55) / 0.05 * (0.7534 - (0.899)) else if fn <= 0.65 ? 0.7534 + (fn - 0.60) / 0.05 * (0.323 - (0.7534)) else if fn <= 0.70 ? 0.323 + (fn - 0.65) / 0.05 * (0.4973 - (0.323)) else if fn <= 0.75 ? 0.4973 + (fn - 0.70) / 0.05 * (-1.5479 - (0.4973)) else -1.5479;
        attribute a6 : Real = if fn <= 0.20 ? 0.0001 + (fn - 0.15) / 0.05 * (0.0005 - (0.0001)) else if fn <= 0.25 ? 0.0005 + (fn - 0.20) / 0.05 * (0.001 - (0.0005)) else if fn <= 0.30 ? 0.001 + (fn - 0.25) / 0.05 * (0.0015 - (0.001)) else if fn <= 0.35 ? 0.0015 + (fn - 0.30) / 0.05 * (0.0021 - (0.0015)) else if fn <= 0.40 ? 0.0021 + (fn - 0.35) / 0.05 * (0.0045 - (0.0021)) else if fn <= 0.45 ? 0.0045 + (fn - 0.40) / 0.05 * (0.0081 - (0.0045)) else if fn <= 0.50 ? 0.0081 + (fn - 0.45) / 0.05 * (0.0106 - (0.0081)) else if fn <= 0.55 ? 0.0106 + (fn - 0.50) / 0.05 * (0.0096 - (0.0106)) else if fn <= 0.60 ? 0.0096 + (fn - 0.55) / 0.05 * (0.01 - (0.0096)) else if fn <= 0.65 ? 0.01 + (fn - 0.60) / 0.05 * (0.0072 - (0.01)) else if fn <= 0.70 ? 0.0072 + (fn - 0.65) / 0.05 * (0.0038 - (0.0072)) else if fn <= 0.75 ? 0.0038 + (fn - 0.70) / 0.05 * (-0.0115 - (0.0038)) else -0.0115;
        attribute a7 : Real = if fn <= 0.20 ? 0.0052 + (fn - 0.15) / 0.05 * (-0.002 - (0.0052)) else if fn <= 0.25 ? -0.002 + (fn - 0.20) / 0.05 * (-0.0043 - (-0.002)) else if fn <= 0.30 ? -0.0043 + (fn - 0.25) / 0.05 * (-0.0172 - (-0.0043)) else if fn <= 0.35 ? -0.0172 + (fn - 0.30) / 0.05 * (-0.0078 - (-0.0172)) else if fn <= 0.40 ? -0.0078 + (fn - 0.35) / 0.05 * (0.1115 - (-0.0078)) else if fn <= 0.45 ? 0.1115 + (fn - 0.40) / 0.05 * (0.2086 - (0.1115)) else if fn <= 0.50 ? 0.2086 + (fn - 0.45) / 0.05 * (0.1336 - (0.2086)) else if fn <= 0.55 ? 0.1336 + (fn - 0.50) / 0.05 * (-0.2272 - (0.1336)) else if fn <= 0.60 ? -0.2272 + (fn - 0.55) / 0.05 * (-0.3352 - (-0.2272)) else if fn <= 0.65 ? -0.3352 + (fn - 0.60) / 0.05 * (-0.4632 - (-0.3352)) else if fn <= 0.70 ? -0.4632 + (fn - 0.65) / 0.05 * (-0.4477 - (-0.4632)) else if fn <= 0.75 ? -0.4477 + (fn - 0.70) / 0.05 * (-0.0977 - (-0.4477)) else -0.0977;
        return result : Real [8] ordered nonunique;
        (a0,a1,a2,a3,a4,a5,a6,a7)
    }
    calc def InputChecks {
        in h : Real [9] ordered nonunique;
        in speed : Real;
        in density : Real;
        in gravity : Real;
        attribute positiveInputs : Real = if h#(1) > 0 and h#(2) > 0 and h#(3) > 0 and h#(4) > 0 and h#(5) > 0 and h#(6) > 0 and h#(7) > 0 and h#(8) > 0 and h#(9) > 0 and speed > 0 and density > 0 and gravity > 0 ? 1.0 else 0.0;
        return result : Real;
        positiveInputs
    }
    calc def Evaluate {
        in h : Real [9] ordered nonunique;
        in speed : Real;
        in density : Real;
        in gravity : Real;
        doc /* h: upright static Lwl, Bwl, canoe-body draft, canoe-body displacement,
         * waterplane area, LCB distance aft of forward perpendicular, LCF distance
         * aft of forward perpendicular, prismatic coefficient, midship coefficient.
         * Lengths metres, area m2, displacement m3; speed m/s, density kg/m3.
         * Caller rejects nonpositive dimensions and any negative domain margin.
         * Negative regression resistance is exposed, never silently clamped. */
        attribute fn : Real = speed / (gravity*h#(1))**0.5;
        attribute a : Real [8] ordered nonunique = Coefficients(fn);
        attribute lcb : Real = h#(6)/h#(1);
        attribute cp : Real = h#(8);
        attribute volumeArea : Real = h#(4)**(2.0/3.0)/h#(5);
        attribute beamLength : Real = h#(2)/h#(1);
        attribute centers : Real = h#(6)/h#(7);
        attribute volumeLength : Real = h#(4)**(1.0/3.0)/h#(1);
        attribute cm : Real = h#(9);
        attribute beamDraft : Real = h#(2)/h#(3);
        attribute ratio : Real = a#(1) + volumeLength * (a#(2)*lcb + a#(3)*cp + a#(4)*volumeArea + a#(5)*beamLength + a#(6)*centers + a#(7)*beamDraft + a#(8)*cm);
        attribute resistance : Real = ratio*density*gravity*h#(4);
        attribute resistance_N : Real = resistance;
        attribute resistance_weight_ratio : Real = ratio;
        attribute froude : Real = fn;
        attribute froude_lower : Real = fn-0.15;
        attribute froude_upper : Real = 0.60-fn;
        attribute lcb_lower : Real = lcb-0.500;
        attribute lcb_upper : Real = 0.582-lcb;
        attribute cp_lower : Real = cp-0.519;
        attribute cp_upper : Real = 0.599-cp;
        attribute volume_area_lower : Real = volumeArea-0.079;
        attribute volume_area_upper : Real = 0.265-volumeArea;
        attribute beam_length_lower : Real = beamLength-0.170;
        attribute beam_length_upper : Real = 0.366-beamLength;
        attribute center_ratio_lower : Real = centers-0.920;
        attribute center_ratio_upper : Real = 1.002-centers;
        attribute volume_length_lower : Real = volumeLength-0.120;
        attribute volume_length_upper : Real = 0.230-volumeLength;
        attribute cm_lower : Real = cm-0.646;
        attribute cm_upper : Real = 0.790-cm;
        attribute beam_draft_lower : Real = beamDraft-2.46;
        attribute beam_draft_upper : Real = 19.38-beamDraft;
        return result : Real [21] ordered nonunique;
        (resistance_N,resistance_weight_ratio,froude,froude_lower,froude_upper,lcb_lower,lcb_upper,cp_lower,cp_upper,volume_area_lower,volume_area_upper,beam_length_lower,beam_length_upper,center_ratio_lower,center_ratio_upper,volume_length_lower,volume_length_upper,cm_lower,cm_upper,beam_draft_lower,beam_draft_upper)
    }
}

package MarineHydrostatics {
    private import ScalarValues::*;
    doc /* Geometry kernel for full-angle static buoyancy. SI metres and cubic
     * metres; points are in world axes with Z up and gravity along -Z.
     * A watertight displacement body is partitioned into nonoverlapping tetrahedra.
     * The external numerical solver supplies pose and solves waterline equilibrium.
     * Flooded voids must be excluded from displacement geometry, not made heavy
     * as well unless retained water is separately trapped. No dynamic recovery claim. */
    calc def Vertex {
        in p : Real [*] ordered nonunique;
        in i : Integer;
        return xyz : Real [3] ordered nonunique;
        if i == 1 ? (p#(1),p#(2),p#(3)) else if i == 2 ? (p#(4),p#(5),p#(6)) else if i == 3 ? (p#(7),p#(8),p#(9)) else (p#(10),p#(11),p#(12))
    }
    calc def Moment {
        in p : Real [12] ordered nonunique;
        attribute ax : Real = p#(4)-p#(1);
        attribute ay : Real = p#(5)-p#(2);
        attribute az : Real = p#(6)-p#(3);
        attribute bx : Real = p#(7)-p#(1);
        attribute byy : Real = p#(8)-p#(2);
        attribute bz : Real = p#(9)-p#(3);
        attribute cx : Real = p#(10)-p#(1);
        attribute cy : Real = p#(11)-p#(2);
        attribute cz : Real = p#(12)-p#(3);
        attribute volume : Real = RealFunctions::abs(ax*(byy*cz-bz*cy)-ay*(bx*cz-bz*cx)+az*(bx*cy-byy*cx))/6;
        return moments : Real [4] ordered nonunique;
        (volume, volume*(p#(1)+p#(4)+p#(7)+p#(10))/4,
            volume*(p#(2)+p#(5)+p#(8)+p#(11))/4,
            volume*(p#(3)+p#(6)+p#(9)+p#(12))/4)
    }
    calc def Intersection {
        in a : Real [3] ordered nonunique;
        in b : Real [3] ordered nonunique;
        in waterline : Real;
        attribute t : Real = (waterline-a#(3))/(b#(3)-a#(3));
        return xyz : Real [3] ordered nonunique;
        (a#(1)+t*(b#(1)-a#(1)), a#(2)+t*(b#(2)-a#(2)), waterline)
    }
    calc def WetMoment {
        in p : Real [12] ordered nonunique;
        in waterline : Real;
        attribute wet : Integer [*] ordered nonunique = (1..4)->ControlFunctions::select { in i : Integer; (Vertex(p,i))#(3) <= waterline };
        attribute dry : Integer [*] ordered nonunique = (1..4)->ControlFunctions::select { in i : Integer; (Vertex(p,i))#(3) > waterline };
        attribute count : Integer = SequenceFunctions::size(wet);
        attribute clipped : Real [4] ordered nonunique = if count == 0 ? (0.0,0.0,0.0,0.0) else
        if count == 4 ? Moment(p) else PartialMoment(p,waterline,(wet,dry),count);
        attribute volume : Real = clipped#(1);
        attribute firstMomentX : Real = clipped#(2);
        attribute firstMomentY : Real = clipped#(3);
        attribute firstMomentZ : Real = clipped#(4);
        return moments : Real [4] ordered nonunique;
        (volume,firstMomentX,firstMomentY,firstMomentZ)
    }
    calc def PartialMoment {
        in p : Real [12] ordered nonunique;
        in waterline : Real;
        in order : Integer [4] ordered nonunique;
        in count : Integer;
        attribute a : Real [3] ordered nonunique = Vertex(p,order#(1));
        attribute b : Real [3] ordered nonunique = Vertex(p,order#(2));
        attribute c : Real [3] ordered nonunique = Vertex(p,order#(3));
        attribute d : Real [3] ordered nonunique = Vertex(p,order#(4));
        return moments : Real [4] ordered nonunique;
        if count == 1 ? Moment((a,Intersection(a,b,waterline),Intersection(a,c,waterline),Intersection(a,d,waterline))) else
        if count == 3 ? Difference(Moment(p),Moment((d,Intersection(d,a,waterline),Intersection(d,b,waterline),Intersection(d,c,waterline)))) else
        TwoWet(a,b,c,d,waterline)
    }
    calc def Difference {
        in a : Real [4] ordered nonunique;
        in b : Real [4] ordered nonunique;
        return values : Real [4] ordered nonunique;
        (a#(1)-b#(1),a#(2)-b#(2),a#(3)-b#(3),a#(4)-b#(4))
    }
    calc def TwoWet {
        in a : Real [3] ordered nonunique;
        in b : Real [3] ordered nonunique;
        in c : Real [3] ordered nonunique;
        in d : Real [3] ordered nonunique;
        in waterline : Real;
        attribute ac : Real [3] ordered nonunique = Intersection(a,c,waterline);
        attribute ad : Real [3] ordered nonunique = Intersection(a,d,waterline);
        attribute bc : Real [3] ordered nonunique = Intersection(b,c,waterline);
        attribute bd : Real [3] ordered nonunique = Intersection(b,d,waterline);
        attribute r1 : Real [4] ordered nonunique = Moment((a,ac,ad,b));
        attribute r2 : Real [4] ordered nonunique = Moment((b,ac,ad,bc));
        attribute r3 : Real [4] ordered nonunique = Moment((b,ad,bc,bd));
        return values : Real [4] ordered nonunique;
        (r1#(1)+r2#(1)+r3#(1),r1#(2)+r2#(2)+r3#(2),r1#(3)+r2#(3)+r3#(3),r1#(4)+r2#(4)+r3#(4))
    }
    calc def MeshMoments {
        in vertices : Real [*] ordered nonunique;
        in waterline : Real;
        in count : Integer;
        attribute rows : Real [*] ordered nonunique = (1..count)->ControlFunctions::collect { in i : Integer;
            WetMoment((1..12)->ControlFunctions::collect { in j : Integer; vertices#(12*(i-1)+j) },waterline) };
        return values : Real [4] ordered nonunique;
        (NumericalFunctions::sum((1..count)->ControlFunctions::collect { in i : Integer; rows#(4*i-3) }),
            NumericalFunctions::sum((1..count)->ControlFunctions::collect { in i : Integer; rows#(4*i-2) }),
            NumericalFunctions::sum((1..count)->ControlFunctions::collect { in i : Integer; rows#(4*i-1) }),
            NumericalFunctions::sum((1..count)->ControlFunctions::collect { in i : Integer; rows#(4*i) }))
    }
    calc def BalanceChecks {
        in massKg : Real;
        in densityKgM3 : Real;
        return positiveMassAndDensity : Real;
        if massKg > 0 and densityKgM3 > 0 ? 1.0 else 0.0
    }
    calc def Balance {
        in moments : Real [4] ordered nonunique;
        in centerOfGravity : Real [3] ordered nonunique;
        in massKg : Real;
        in densityKgM3 : Real;
        attribute g : Real = 9.80665;
        attribute massResidual : Real = densityKgM3*moments#(1)-massKg;
        attribute rollTorque : Real = g*(densityKgM3*moments#(3)-massKg*centerOfGravity#(2));
        attribute pitchTorque : Real = -g*(densityKgM3*moments#(2)-massKg*centerOfGravity#(1));
        return values : Real [3] ordered nonunique;
        (massResidual,rollTorque,pitchTorque)
    }

    calc def BuoyancyMomentSensitivity {
        in displacedVolumeM3 : Real;
        in signedHorizontalLeverM : Real;
        in waterDensityKgM3 : Real;
        return momentNm : Real;
        waterDensityKgM3 * 9.80665 * displacedVolumeM3 * signedHorizontalLeverM
    }
}

package MarinePropulsion {
    private import ScalarValues::*;
    calc def IdealAxialDiskPower {
        doc /* Steady ideal axial actuator disk. Inputs: thrust N, diameter m,
         * fluid density kg/m3 and nonnegative axial inflow m/s. Output W.
         * Excludes swirl/profile losses, installation effects, crossflow,
         * ventilation and cavitation. Callers qualify the operating domain. */
        in thrustN : Real;
        in diameterM : Real;
        in densityKgM3 : Real;
        in axialSpeedMS : Real;
        attribute diskAreaM2 : Real = 3.141592653589793 * diameterM * diameterM / 4;
        attribute inducedSpeed : Real = (-axialSpeedMS + RealFunctions::sqrt(axialSpeedMS * axialSpeedMS + 2 * thrustN / (densityKgM3 * diskAreaM2))) / 2;
        return powerW : Real = thrustN * (axialSpeedMS + inducedSpeed);
    }
}

package MarineRecovery {
    private import ScalarValues::*;
    calc def Segment {
        doc /* SI boundary: distance m, installed through-water speed m/s,
         * along-track current m/s, cross-track current m/s, motor and essential
         * battery withdrawal W, uncertainty multiplier. Output: feasible flag,
         * ground speed m/s, transit s, protected energy Wh.
         * Steady crab-angle compensation, no wave or acceleration model.
         * Speed and power must be valid for the declared casualty state.
         */
        in x : Real [7] ordered nonunique;
        attribute valid : Boolean = x#(1) >= 0 and x#(2) > 0 and x#(5) >= 0 and x#(6) > 0 and x#(7) >= 1;
        attribute authority : Boolean = valid and RealFunctions::abs(x#(4)) < x#(2);
        attribute ground : Real = if authority ? RealFunctions::sqrt(x#(2)*x#(2)-x#(4)*x#(4))+x#(3) else 0;
        attribute feasible : Boolean = authority and ground > 0;
        attribute duration : Real = if feasible ? x#(1)/ground else 0;
        attribute feasibleFlag : Real = if feasible ? 1 else 0;
        attribute protectedEnergy : Real = x#(7)*(x#(5)+x#(6))*duration/3600;
        return result : Real [4] ordered nonunique;
        (feasibleFlag,ground,duration,protectedEnergy)
    }
}

package MarineReliability {
    private import ScalarValues::*;
    calc def ConstantHazardSurvival {
        in ratePerHour : Real;
        in hours : Real;
        return survival : Real = OpenSysMLMathFunctions::exp(-ratePerHour * hours);
    }
    calc def EqualSurvivalRate {
        in survival : Real;
        in hours : Real;
        return ratePerHour : Real = -OpenSysMLMathFunctions::ln(survival) / hours;
    }
    doc /* Constant nonnegative mission-critical hazard, no repair, hours > 0,
     * and 0 < target survival <= 1. NIST Engineering Statistics Handbook,
     * https://itl.nist.gov/div898/handbook/apr/section1/apr161.htm.
     * The calculation does not estimate rates or represent impact/cycle damage. */
}

package MarineSailing {
    private import ScalarValues::*;

    calc def Core {
        in d : Real [29] ordered nonunique;
        in p : Real [41] ordered nonunique;
        in q : Real [*] ordered nonunique;
        in s : Real [9] ordered nonunique;
        in aero : Real [3] ordered nonunique;
        in massData : Real [21] ordered nonunique;
        in hydro : Real [12] ordered nonunique;
        in surface : Real [9] ordered nonunique;
        // enabled, Fx, Fy, air roll moment, signed mast moment, min Va, max |CL|, added resistance, incidence margin
        doc /* s: wind, windward flag, fouling multiplier, speed, wind-from heading,
         * incidence, leeway, rudder angle, heel (angles degrees). hydro:
         * waterline Z, restoring moment, wetted hull area, then nine upright static
         * canoe-body metrics from MarineResistance::Evaluate. aero moment at midchord.
         * Axes and equations preserve the existing body-frame convention. */
        attribute lwl_m : Real = hydro#(4);
        attribute beam_m : Real = d#(2);
        attribute sail_m2 : Real = d#(5);
        attribute sail_AR : Real = d#(6);
        attribute keel_m2 : Real = d#(11);
        attribute keel_span_m : Real = d#(12);
        attribute rudder_m2 : Real = d#(13);
        attribute rudder_span_m : Real = d#(14);
        attribute ballast_kg : Real = d#(16);
        attribute sail_x_fraction : Real = d#(10);
        attribute battery_Wh : Real = d#(17);
        attribute panel_m2 : Real = d#(18);
        attribute rudder_arm_fraction : Real = d#(15);
        attribute g : Real = p#(35);
        attribute rho_air : Real = p#(33);
        attribute rho_water : Real = p#(32);
        attribute rho_ballast : Real = p#(34);
        attribute nu_air : Real = p#(30);
        attribute nu_water : Real = p#(31);
        attribute foil_efficiency : Real = p#(28);
        attribute wing_cd0 : Real = p#(15);
        attribute foil_cd0 : Real = p#(29);
        attribute wing_cl_limit : Real = p#(16);
        attribute foil_cl_limit : Real = p#(27);
        attribute load_factor : Real = p#(36);
        attribute residuary_factor : Real = p#(25);
        attribute viscous_form_factor : Real = p#(26);
        attribute solar_resource_factor : Real = p#(12);
        attribute electronics_W : Real = p#(11);
        attribute foil_alpha_limit_deg : Real = q#(1);
        attribute rudder_inflow_ratio : Real = q#(2);
        attribute hinge_fraction : Real = q#(3);
        attribute friction_Nm : Real = q#(4);
        attribute max_froude : Real = q#(5);
        attribute min_wing_Re : Real = q#(6);
        attribute min_foil_Re : Real = q#(7);
        attribute control_speed_m_s : Real = q#(9);
        attribute control_wind_m_s : Real = q#(10);
        attribute peak_irradiance_W_m2 : Real = q#(11);
        attribute panel_efficiency : Real = q#(12);
        attribute harvest_efficiency : Real = q#(13);
        attribute charge_efficiency : Real = q#(14);
        attribute discharge_efficiency : Real = q#(15);
        attribute usable_fraction : Real = q#(16);
        attribute initial_fraction : Real = q#(17);
        attribute charge_C_rate : Real = q#(18);
        attribute discharge_C_rate : Real = q#(19);
        attribute self_discharge_W : Real = q#(20);
        attribute dark_hours : Real = q#(21);
        attribute solar_hours : Real = q#(22);
        attribute reserve_Wh : Real = q#(23);
        attribute yaw_reserve_Nm : Real = q#(8);
        attribute wind : Real = s#(1);
        attribute upwind : Boolean = s#(2) > 0.5;
        attribute foul : Real = s#(3);
        attribute v : Real = s#(4);
        attribute theta : Real = TrigFunctions::rad(s#(5));
        attribute alpha : Real = TrigFunctions::rad(s#(6));
        attribute beta : Real = TrigFunctions::rad(s#(7));
        attribute delta : Real = TrigFunctions::rad(s#(8));
        attribute heel : Real = TrigFunctions::rad(s#(9));
        attribute cb : Real = TrigFunctions::cos(beta);
        attribute sb : Real = TrigFunctions::sin(beta);
        attribute ch : Real = TrigFunctions::cos(heel);
        attribute wingHeight : Real = RealFunctions::sqrt(sail_m2 * sail_AR);
        attribute wingChord : Real = sail_m2 / wingHeight;
        attribute keelChord : Real = keel_m2 / keel_span_m;
        attribute rudderChord : Real = rudder_m2 / rudder_span_m;
        attribute mass : Real = massData#(1);
        attribute draft : Real = hydro#(1)+d#(3);
        attribute wingZ : Real = d#(4)+wingHeight/2-hydro#(1);
        attribute keelZ : Real = draft+keel_span_m/2;
        attribute rudderZ : Real = draft+rudder_span_m/2;
        attribute righting : Real = hydro#(2);
        attribute awx : Real = wind * TrigFunctions::cos(theta) + v * cb;
        attribute awy : Real = wind * TrigFunctions::sin(theta) - v * sb;
        attribute va : Real = RealFunctions::sqrt(awx * awx + awy * awy);
        attribute qa : Real = 0.5 * rho_air * va * va;
        attribute cl : Real = aero#(1)*p#(17);
        attribute cd : Real = (aero#(2)+p#(15))*p#(18);
        attribute xs : Real = if surface#(1)>0.5 ? surface#(2) else qa * sail_m2 * (cl * ch * awy - cd * awx) / va;
        attribute ys : Real = if surface#(1)>0.5 ? surface#(3) else qa * sail_m2 * (cl * ch * awx + cd * awy) / va;
        attribute drive : Real = xs * cb + ys * sb;
        attribute sideNormal : Real = ys * cb - xs * sb;
        attribute qk : Real = 0.5 * rho_water * v * v;
        attribute qr : Real = qk * rudder_inflow_ratio * rudder_inflow_ratio;
        attribute ark : Real = keel_span_m * keel_span_m / keel_m2;
        attribute arr : Real = rudder_span_m * rudder_span_m / rudder_m2;
        attribute foilAlphaLimit : Real = TrigFunctions::rad(foil_alpha_limit_deg);
        attribute clk : Real = 2 * TrigFunctions::pi / (1 + 2 / (foil_efficiency * ark)) * beta * ch;
        attribute clr : Real = 2 * TrigFunctions::pi / (1 + 2 / (foil_efficiency * arr)) * (beta + delta) * ch;
        attribute lk : Real = qk * keel_m2 * clk * ch;
        attribute lr : Real = qr * rudder_m2 * clr * ch;
        attribute dk : Real = qk * keel_m2 * (foil_cd0 * foul + clk * clk / (TrigFunctions::pi * foil_efficiency * ark));
        attribute dr : Real = qr * rudder_m2 * (foil_cd0 * foul + clr * clr / (TrigFunctions::pi * foil_efficiency * arr));
        attribute fn : Real = v / RealFunctions::sqrt(g * lwl_m);
        attribute hullRe : Real = v * lwl_m / nu_water;
        attribute logRe : Real = OpenSysMLMathFunctions::ln(hullRe) / OpenSysMLMathFunctions::ln(10);
        attribute cf : Real = 0.075 / ((logRe - 2) * (logRe - 2));
        attribute wetted : Real = hydro#(3);
        attribute delft : Real [21] ordered nonunique = MarineResistance::Evaluate((hydro#(4),hydro#(5),hydro#(6),hydro#(7),hydro#(8),hydro#(9),hydro#(10),hydro#(11),hydro#(12)),v,rho_water,g);
        attribute hullDrag : Real = qk * wetted * cf * viscous_form_factor * foul + residuary_factor*delft#(1);
        attribute resistance : Real = hullDrag + dk + dr + surface#(8);
        attribute sailX : Real = sail_x_fraction * d#(1);
        attribute rudderX : Real = -rudder_arm_fraction * d#(1);
        attribute heeling : Real = (if surface#(1)>0.5 ? surface#(4) else ys * wingZ * ch) + ((lk * cb + dk * sb) * keelZ + (lr * cb + dr * sb) * rudderZ + hullDrag * sb * draft / 2) * ch;
        attribute rudderTorque : Real = qr * rudder_m2 * RealFunctions::sqrt(clr * clr + foil_cd0 * foil_cd0) * hinge_fraction * rudderChord + friction_Nm;
        attribute rudderEnvelopeTorque : Real = qr * rudder_m2 * foil_cl_limit * hinge_fraction * rudderChord + friction_Nm;
        attribute waterVMG : Real = (if upwind ? 1 else -1) * v * TrigFunctions::cos(theta + beta);
        attribute wingRe : Real = (if surface#(1)>0.5 ? surface#(6) else va) * wingChord / nu_air;
        attribute keelRe : Real = v * keelChord / nu_water;
        attribute rudderRe : Real = v * rudder_inflow_ratio * rudderChord / nu_water;
        attribute normalCoefficient : Real = cl*TrigFunctions::cos(alpha)+cd*TrigFunctions::sin(alpha);
        attribute mastMomentCoefficient : Real = aero#(3)*q#(24)+((if s#(5)<0 ? 1-d#(9) else d#(9))-0.5)*normalCoefficient;
        attribute wingTorque : Real = if surface#(1)>0.5 ? RealFunctions::abs(surface#(5))+friction_Nm else MarineActuation::MastTorque(rho_air,va,sail_m2,wingChord,mastMomentCoefficient,friction_Nm);
        attribute wingPower : Real [3] ordered nonunique = MarineActuation::DrivePower(wingTorque,p#(19),p#(3),p#(2),p#(4),p#(5),p#(6),p#(7),p#(8));
        attribute rudderPower : Real [3] ordered nonunique = MarineActuation::DrivePower(rudderTorque,p#(20),p#(3),1,1,0.1,p#(9)*rudderTorque,p#(10),1-p#(10));
        attribute averagePower : Real = electronics_W+wingPower#(1)+rudderPower#(1);
        attribute peakPower : Real = electronics_W+wingPower#(2)+rudderPower#(2);
        attribute harvestPower : Real = panel_m2 * peak_irradiance_W_m2 * panel_efficiency * harvest_efficiency * solar_resource_factor;
        attribute nightRate : Real = -averagePower / discharge_efficiency - self_discharge_W;
        attribute dayRate : Real = (if harvestPower >= averagePower ? NumericalFunctions::min((harvestPower - averagePower) * charge_efficiency, charge_C_rate * battery_Wh) else (harvestPower - averagePower) / discharge_efficiency) - self_discharge_W;
        attribute cycleEnergy : Real = dark_hours * nightRate + solar_hours * dayRate;
        attribute reserveMargin : Real = initial_fraction * usable_fraction * battery_Wh + dark_hours * nightRate - reserve_Wh;
        attribute surgeResidual : Real = (drive-resistance)/10;
        attribute swayResidual : Real = (sideNormal-lk-lr)/10;
        attribute yawResidual : Real = (-ys*sailX+(lr*cb+dr*sb)*rudderX-(if surface#(1)>0.5 ? surface#(5) else qa*sail_m2*wingChord*mastMomentCoefficient))/10;
        attribute rollResidual : Real = (righting-heeling)/20;
        attribute wingLiftMargin : Real = if surface#(1)>0.5 ? NumericalFunctions::min(1-surface#(7)/wing_cl_limit,surface#(9)) else 1-RealFunctions::abs(cl)/wing_cl_limit;
        attribute keelLiftMargin : Real = 1-RealFunctions::abs(clk)/foil_cl_limit;
        attribute rudderLiftMargin : Real = 1-RealFunctions::abs(clr)/foil_cl_limit;
        attribute keelAngleMargin : Real = 1-RealFunctions::abs(beta*ch)/foilAlphaLimit;
        attribute rudderAngleMargin : Real = 1-RealFunctions::abs((beta+delta)*ch)/foilAlphaLimit;
        attribute wingDriveMargin : Real = 1-load_factor*wingTorque/d#(19);
        attribute rudderDriveMargin : Real = 1-load_factor*rudderEnvelopeTorque/d#(20);
        attribute froudeMargin : Real = 1-fn/max_froude;
        attribute wingReMargin : Real = wingRe/min_wing_Re-1;
        attribute keelReMargin : Real = keelRe/min_foil_Re-1;
        attribute rudderReMargin : Real = rudderRe/min_foil_Re-1;
        attribute cycleMargin : Real = cycleEnergy/100;
        attribute reserveMarginScaled : Real = reserveMargin/100;
        attribute peakMargin : Real = (discharge_C_rate*battery_Wh-peakPower/discharge_efficiency-self_discharge_W)/100;
        attribute wingResultant : Real = if surface#(1)>0.5 ? RealFunctions::sqrt(xs*xs+ys*ys) else qa*sail_m2*RealFunctions::sqrt(cl*cl+cd*cd);
        attribute keelResultant : Real = RealFunctions::sqrt(lk*lk+dk*dk);
        attribute rudderResultant : Real = RealFunctions::sqrt(lr*lr+dr*dr);
        attribute delftResistanceMargin : Real = delft#(2);
        attribute delftDomain4 : Real = delft#(4);
        attribute delftDomain5 : Real = delft#(5);
        attribute delftDomain6 : Real = delft#(6);
        attribute delftDomain7 : Real = delft#(7);
        attribute delftDomain8 : Real = delft#(8);
        attribute delftDomain9 : Real = delft#(9);
        attribute delftDomain10 : Real = delft#(10);
        attribute delftDomain11 : Real = delft#(11);
        attribute delftDomain12 : Real = delft#(12);
        attribute delftDomain13 : Real = delft#(13);
        attribute delftDomain14 : Real = delft#(14);
        attribute delftDomain15 : Real = delft#(15);
        attribute delftDomain16 : Real = delft#(16);
        attribute delftDomain17 : Real = delft#(17);
        attribute delftDomain18 : Real = delft#(18);
        attribute delftDomain19 : Real = delft#(19);
        attribute delftDomain20 : Real = delft#(20);
        attribute delftDomain21 : Real = delft#(21);
        return result : Real [*] ordered nonunique;
        (surgeResidual, swayResidual, yawResidual, rollResidual, wingLiftMargin, keelLiftMargin, rudderLiftMargin, keelAngleMargin, rudderAngleMargin, wingDriveMargin, rudderDriveMargin, froudeMargin, wingReMargin, keelReMargin, rudderReMargin, cycleMargin, reserveMarginScaled, peakMargin, waterVMG, v, cl, cd, clk, clr, drive, resistance, heeling, righting, wingTorque, rudderTorque, averagePower, peakPower, harvestPower, cycleEnergy, reserveMargin, wingRe, keelRe, rudderRe, ys, lk, lr, hullDrag, dk, dr, wingResultant, keelResultant, rudderResultant, delftResistanceMargin, delftDomain4, delftDomain5, delftDomain6, delftDomain7, delftDomain8, delftDomain9, delftDomain10, delftDomain11, delftDomain12, delftDomain13, delftDomain14, delftDomain15, delftDomain16, delftDomain17, delftDomain18, delftDomain19, delftDomain20, delftDomain21)
    }

    calc def Evaluate {
        in d : Real [29] ordered nonunique;
        in p : Real [41] ordered nonunique;
        in q : Real [*] ordered nonunique;
        in s : Real [9] ordered nonunique;
        in aero : Real [3] ordered nonunique;
        in massData : Real [21] ordered nonunique;
        in hydro : Real [12] ordered nonunique;
        return result : Real [*] ordered nonunique;
        Core(d,p,q,s,aero,massData,hydro,(hydro#(1)*0,hydro#(1)*0,hydro#(1)*0,hydro#(1)*0,hydro#(1)*0,hydro#(1)*0,hydro#(1)*0,hydro#(1)*0,hydro#(1)*0))
    }
    calc def InputChecks {
        doc /* Executable numerical preconditions shared by scalar and batch
         * operating evaluation. Each output is one for valid, zero otherwise. */
        in p : Real [41] ordered nonunique;
        in s : Real [9] ordered nonunique;
        in hydro : Real [12] ordered nonunique;
        attribute driveEfficiencies : Real = if p#(2) > 0 and p#(2) <= 1 and p#(3) > 0 and p#(3) <= 1 ? 1.0 else 0.0;
        attribute wingDuty : Real = if p#(7) >= 0 and p#(8) >= 0 and p#(7)+p#(8) <= 1.000000000001 ? 1.0 else 0.0;
        attribute rudderDuty : Real = if p#(10) >= 0 and p#(10) <= 1 ? 1.0 else 0.0;
        attribute positiveSpeed : Real = if s#(4) > 0 ? 1.0 else 0.0;
        attribute positiveWettedArea : Real = if hydro#(3) > 0 ? 1.0 else 0.0;
        return result : Real [5] ordered nonunique;
        (driveEfficiencies,wingDuty,rudderDuty,positiveSpeed,positiveWettedArea)
    }
}

package MarineSurface {
    private import ScalarValues::*;
    doc /* SI magnitudes. Neutral log profile and strip quadrature are a first
     * surface-layer screen, not a stability-corrected wave boundary-layer model.
     * Wave resistance is an explicitly uncalibrated sensitivity coefficient.
     * Deep-water wave/current action transport assumes slow spatial variation;
     * a uniform river current is not itself a shoaling transition. */
    calc def WindSample {
        in x : Real [9] ordered nonunique;
        // reference wind, reference height, roughness, sample height, heading,
        // vessel speed, leeway (radians), shear enabled, minimum valid height.
        attribute height : Real = NumericalFunctions::max(x#(4),x#(9));
        attribute ratio : Real = if x#(8)>0.5 ? OpenSysMLMathFunctions::ln(height/x#(3))/OpenSysMLMathFunctions::ln(x#(2)/x#(3)) else 1;
        attribute ax : Real = x#(1)*ratio*TrigFunctions::cos(x#(5))+x#(6)*TrigFunctions::cos(x#(7));
        attribute ay : Real = x#(1)*ratio*TrigFunctions::sin(x#(5))-x#(6)*TrigFunctions::sin(x#(7));
        attribute speed : Real = RealFunctions::sqrt(ax*ax+ay*ay);
        attribute heightMargin : Real = x#(4)/x#(9)-1;
        return result : Real [5] ordered nonunique;
        (ratio,ax,ay,speed,heightMargin)
    }
    calc def StripLoad {
        in x : Real [10] ordered nonunique;
        // rho, strip area, apparent x/y, heel rad, height above mean water,
        // CL, CD, chord, signed mast moment coefficient.
        attribute va : Real = RealFunctions::sqrt(x#(3)*x#(3)+x#(4)*x#(4));
        attribute pressureArea : Real = 0.5*x#(1)*va*va*x#(2);
        attribute xs : Real = pressureArea*(x#(7)*TrigFunctions::cos(x#(5))*x#(4)-x#(8)*x#(3))/va;
        attribute ys : Real = pressureArea*(x#(7)*TrigFunctions::cos(x#(5))*x#(3)+x#(8)*x#(4))/va;
        attribute rollMoment : Real = ys*x#(6);
        attribute mastMoment : Real = pressureArea*x#(9)*x#(10);
        return result : Real [4] ordered nonunique;
        (xs,ys,rollMoment,mastMoment)
    }
    calc def FetchSea {
        in x : Real [3] ordered nonunique;
        // reference 10 m wind, effective fetch, gravity; SMB deep-water growth.
        attribute wind : Real = NumericalFunctions::max(x#(1),0.1);
        attribute fetch : Real = x#(3)*x#(2)/(wind*wind);
        attribute hArg : Real = 0.0125*OpenSysMLMathFunctions::exp(0.42*OpenSysMLMathFunctions::ln(fetch));
        attribute tArg : Real = 0.077*OpenSysMLMathFunctions::exp(0.25*OpenSysMLMathFunctions::ln(fetch));
        attribute hTanh : Real = (1-OpenSysMLMathFunctions::exp(-2*hArg))/(1+OpenSysMLMathFunctions::exp(-2*hArg));
        attribute tTanh : Real = (1-OpenSysMLMathFunctions::exp(-2*tArg))/(1+OpenSysMLMathFunctions::exp(-2*tArg));
        attribute height : Real = if x#(1)>0 ? 0.283*wind*wind/x#(3)*hTanh else 0;
        attribute period : Real = NumericalFunctions::max(1,2*TrigFunctions::pi*1.2*wind/x#(3)*tTanh);
        return result : Real [2] ordered nonunique;
        (height,period)
    }
    calc def SpeedRetention {
        in x : Real [2] ordered nonunique;
        // Added resistance and calm-water resistance at the solved state.
        // Local R ~ V^2 and unchanged available thrust: sensitivity, not a VPP.
        attribute ratio : Real = RealFunctions::sqrt(NumericalFunctions::max(0,1-x#(1)/x#(2)));
        return result : Real [1] ordered nonunique;
        (ratio)
    }
    calc def WaveScreen {
        in x : Real [13] ordered nonunique;
        // incident Hs, absolute period, current along propagation, L, B,
        // water-relative speed, cos(wave-to minus heading), resistance coeff,
        // freeboard, wing-root height, appendage-tip immersion, g, rho.
        attribute omega : Real = 2*TrigFunctions::pi/x#(2);
        attribute discriminant : Real = x#(12)+4*x#(3)*omega;
        attribute root : Real = RealFunctions::sqrt(NumericalFunctions::max(discriminant,0.000001));
        attribute sqrtK : Real = 2*omega/(root+RealFunctions::sqrt(x#(12)));
        attribute k : Real = sqrtK*sqrtK;
        attribute sigma : Real = RealFunctions::sqrt(x#(12)*k);
        attribute groupSpeed : Real = 0.5*RealFunctions::sqrt(x#(12)/k);
        attribute absoluteGroup : Real = groupSpeed+x#(3);
        attribute incidentGroup : Real = x#(12)/(2*omega);
        attribute height : Real = x#(1)*RealFunctions::sqrt(sigma*incidentGroup/(omega*NumericalFunctions::max(absoluteGroup,0.000001)));
        attribute wavelength : Real = 2*TrigFunctions::pi/k;
        attribute encounter : Real = RealFunctions::abs(sigma-k*x#(6)*x#(7));
        attribute coupling : Real = NumericalFunctions::min(1,k*k*x#(4)*x#(4));
        attribute resistance : Real = x#(8)*x#(13)*x#(12)*x#(5)*height*height/16*coupling*(0.25+0.375*(1-x#(7)));
        attribute blockingMargin : Real = discriminant/x#(12);
        attribute steepnessMargin : Real = 0.1-height/wavelength;
        attribute hullClearance : Real = x#(9)-height;
        attribute wingClearance : Real = x#(10)-height;
        attribute appendageImmersion : Real = x#(11)-height;
        return result : Real [9] ordered nonunique;
        (height,wavelength,encounter,resistance,blockingMargin,steepnessMargin,hullClearance,wingClearance,appendageImmersion)
    }
    calc def HarmonicResponse {
        in x : Real [7] ordered nonunique;
        // Wave amplitude, wavenumber, signed encounter frequency, phase,
        // relative propagation heading, heave gain, slope gain. Wave phase
        // increases as k*x - omega*t; pitch is rotation about body +y.
        attribute a : Real = x#(1);
        attribute phase : Real = x#(4);
        attribute slope : Real = -a*x#(2)*TrigFunctions::sin(phase)*x#(7);
        attribute slopeRate : Real = a*x#(2)*x#(3)*TrigFunctions::cos(phase)*x#(7);
        attribute heave : Real = a*TrigFunctions::cos(phase)*x#(6);
        attribute pitch : Real = -slope*TrigFunctions::cos(x#(5));
        attribute roll : Real = slope*TrigFunctions::sin(x#(5));
        attribute heaveRate : Real = a*x#(3)*TrigFunctions::sin(phase)*x#(6);
        attribute pitchRate : Real = -slopeRate*TrigFunctions::cos(x#(5));
        attribute rollRate : Real = slopeRate*TrigFunctions::sin(x#(5));
        return result : Real [6] ordered nonunique;
        (heave,pitch,roll,heaveRate,pitchRate,rollRate)
    }
}

package MarineWavePerformance {
    private import ScalarValues::*;
    calc def OrbitalVelocity {
        in x : Real [7] ordered nonunique;
        // amplitude, k, intrinsic omega, depth z<=0, phase, direction, gravity.
        attribute decay : Real = OpenSysMLMathFunctions::exp(x#(2)*NumericalFunctions::min(x#(4),0));
        attribute scale : Real = x#(1)*x#(3)*decay;
        attribute vx : Real = scale*TrigFunctions::cos(x#(5))*TrigFunctions::cos(x#(6));
        attribute vy : Real = scale*TrigFunctions::cos(x#(5))*TrigFunctions::sin(x#(6));
        attribute vz : Real = scale*TrigFunctions::sin(x#(5));
        return result : Real [3] ordered nonunique;
        (vx,vy,vz)
    }
    calc def FoilLoad {
        in x : Real [12] ordered nonunique;
        // rho, area, span, relative speed, incidence rad, heel rad,
        // efficiency, profile Cd, fouling, CL limit, alpha limit rad, wet fraction.
        attribute ar : Real = x#(3)*x#(3)/x#(2);
        attribute cl : Real = 2*TrigFunctions::pi/(1+2/(x#(7)*ar))*x#(5)*TrigFunctions::cos(x#(6));
        attribute pressure : Real = 0.5*x#(1)*x#(4)*x#(4)*x#(2)*x#(12);
        attribute lift : Real = pressure*cl*TrigFunctions::cos(x#(6));
        attribute drag : Real = pressure*(x#(8)*x#(9)+cl*cl/(TrigFunctions::pi*x#(7)*ar));
        attribute liftMargin : Real = 1-RealFunctions::abs(cl)/x#(10);
        attribute angleMargin : Real = 1-RealFunctions::abs(x#(5)*TrigFunctions::cos(x#(6)))/x#(11);
        return result : Real [4] ordered nonunique;
        (lift,drag,liftMargin,angleMargin)
    }
    calc def ImpedanceTerm {
        in x : Real [6] ordered nonunique;
        // encounter omega, rigid mass, added mass, stiffness, radiation damping, extra damping.
        attribute realPart : Real = x#(4)-x#(1)*x#(1)*(x#(2)+x#(3));
        attribute imaginaryPart : Real = -x#(1)*(x#(5)+x#(6));
        return result : Real [2] ordered nonunique;
        (realPart,imaginaryPart)
    }
    calc def BalanceCorrection {
        in x : Real [12] ordered nonunique;
        // baseline four normalized residuals; old/new total appendage drag,
        // old/new total lift; old/new water yaw moment; old/new water roll moment.
        attribute surgeResidual : Real = x#(1)+(x#(5)-x#(6))/10;
        attribute swayResidual : Real = x#(2)+(x#(7)-x#(8))/10;
        attribute yawResidual : Real = x#(3)+(x#(10)-x#(9))/10;
        attribute rollResidual : Real = x#(4)+(x#(11)-x#(12))/20;
        return result : Real [4] ordered nonunique;
        (surgeResidual,swayResidual,yawResidual,rollResidual)
    }
    calc def Actuation {
        in p : Real [41] ordered nonunique;
        in q : Real [*] ordered nonunique;
        in x : Real [3] ordered nonunique;
        // Wing torque, rudder torque, battery Wh; same duty model as Core.
        attribute wing : Real [3] ordered nonunique = MarineActuation::DrivePower(x#(1),p#(19),p#(3),p#(2),p#(4),p#(5),p#(6),p#(7),p#(8));
        attribute rudder : Real [3] ordered nonunique = MarineActuation::DrivePower(x#(2),p#(20),p#(3),1,1,0.1,p#(9)*x#(2),p#(10),1-p#(10));
        attribute peak : Real = p#(11)+wing#(2)+rudder#(2);
        attribute averagePower : Real = p#(11)+wing#(1)+rudder#(1);
        attribute peakMargin : Real = (q#(19)*x#(3)-peak/q#(15)-q#(20))/100;
        return result : Real [3] ordered nonunique;
        (averagePower,peak,peakMargin)
    }
}

package MarineWeather {
    private import ScalarValues::*;
    calc def TwoRegimeCoverage {
        in eastProbability : Real;
        in westPass : Boolean;
        in eastPass : Boolean;
        return coverage : Real;
        (1-eastProbability)*(if westPass ? 1 else 0) + eastProbability*(if eastPass ? 1 else 0)
    }
    calc def ConditionalPassageHours {
        in eastProbability : Real;
        in westPass : Boolean;
        in eastPass : Boolean;
        in westHours : Real;
        in eastHours : Real;
        attribute coverage : Real = TwoRegimeCoverage(eastProbability,westPass,eastPass);
        return hours : Real;
        if coverage > 0 ? ((1-eastProbability)*(if westPass ? westHours else 0) + eastProbability*(if eastPass ? eastHours else 0))/coverage else 0
    }
    doc /* Arithmetic for two mutually exclusive full-passage regime hypotheses.
     * Caller must validate 0<=p<=1, finite nonnegative times for passing cases,
     * and report coverage=0 as no conditional time (not a zero-hour passage).
     * Station hourly direction fractions are not full-passage probabilities.
     * Coverage is a route-screen sensitivity, not system reliability. */
}

package InlandExtended {
    doc /* Reusable U.S. Inland Rules interpretation. Supplied facts and candidate checks are conditional assessments, not established legal compliance. The mission navigation adapter consumes the pair assessment; equipment and other obligations remain separately assessed.*/
    private import ScalarValues::*;
    enum def Truth { yes; no; unknown; }
    enum def Mode { sail; power; rowing; towingAstern; pushing; towed; pushed; trawling; fishing; nuc; ram; dredging; diving; mineClearance; pilot; seaplane; wig; airCushion; mooredBarge; }
    enum def Side { portSide; starboardSide; ahead; aft; unresolved; }
    part context;
    analysis def General {
        doc /* Rules 1-8. Candidate-action and evidence checks, not a sensor estimator or safe-speed optimizer. Judgment inputs require external evidence; no universal CPA/time/turn threshold is invented. Rule 4 applies general duties in all visibility. Rule 3 definitions are externally classified facts. Rule 2 departure requires assessed necessity, never a blanket emergency exemption.*/
        subject encounter;
        in attribute factsKnown : Boolean;
        in attribute inlandWaters : Boolean;
        in attribute jurisdictionReviewed : Boolean;
        in attribute localProvisionsSatisfied : Boolean;
        in attribute visualLookout : Boolean;
        in attribute hearingLookout : Boolean;
        in attribute appropriateMeansUsed : Boolean;
        in attribute radarOperational : Boolean;
        in attribute radarLongRangeUsed : Boolean;
        in attribute radarPlottingUsed : Boolean;
        in attribute visibilityReviewed : Boolean;
        in attribute trafficDensityReviewed : Boolean;
        in attribute maneuverabilityReviewed : Boolean;
        in attribute backgroundLightsReviewed : Boolean;
        in attribute weatherCurrentReviewed : Boolean;
        in attribute draftDepthReviewed : Boolean;
        in attribute radarLimitsReviewed : Boolean;
        in attribute positiveAction : Boolean;
        in attribute earlyAction : Boolean;
        in attribute substantialAction : Boolean;
        in attribute noNewCloseQuarters : Boolean;
        in attribute safePassingDistance : Boolean;
        in attribute effectivenessMonitored : Boolean;
        in attribute finallyClear : Boolean;
        in attribute speedReductionNecessary : Boolean;
        in attribute speedReduced : Boolean;
        in attribute immediateDanger : Boolean;
        in attribute departureNecessary : Boolean;
        in attribute departureLimitedToNecessity : Boolean;
        in attribute specialCircumstancesReviewed : Boolean;
        in attribute riskAssessment : InlandExtended::Truth;
        in attribute approaching : Boolean;
        in attribute bearingSteady : Boolean;
        in attribute largeTowOrCloseRange : Boolean;
        in attribute otherRiskEvidence : Boolean;
        out attribute rule1Applicable : Boolean = inlandWaters;
        out attribute rule2DepartureAssessmentSupported : Boolean = factsKnown and immediateDanger and departureNecessary and departureLimitedToNecessity and specialCircumstancesReviewed;
        out attribute rule5Supported : Boolean = factsKnown and visualLookout and hearingLookout and appropriateMeansUsed;
        out attribute rule6Supported : Boolean = factsKnown and visibilityReviewed and trafficDensityReviewed and maneuverabilityReviewed and backgroundLightsReviewed and weatherCurrentReviewed and draftDepthReviewed and (not radarOperational or radarLimitsReviewed);
        out attribute rule7RiskPresent : Boolean = riskAssessment != Truth::no or (approaching and bearingSteady) or otherRiskEvidence;
        out attribute rule7FurtherAppraisalRequired : Boolean = not factsKnown or (largeTowOrCloseRange and approaching) or (radarOperational and (not radarLongRangeUsed or not radarPlottingUsed));
        out attribute rule8MonitorRequired : Boolean = not finallyClear;
        out attribute rule8CandidateSupported : Boolean = factsKnown and positiveAction and earlyAction and substantialAction and noNewCloseQuarters and safePassingDistance and (finallyClear or effectivenessMonitored) and (not speedReductionNecessary or speedReduced);
        out attribute assessmentSupported : Boolean = inlandWaters and jurisdictionReviewed and localProvisionsSatisfied and rule5Supported and rule6Supported and not rule7FurtherAppraisalRequired and rule8CandidateSupported;
        out attribute completeComplianceEstablished : Boolean = false;
    }
    analysis def ChannelsAndTSS {
        doc /* Rules 8(f), 9 and 10. River encounter priority is in Assess; signal exchanges are in Signals. A necessary maintenance/cable exemption is a supplied, clause-limited determination: tssSupported is not overall compliance, and exemptionScopeReviewRequired remains true. Facts about legally designated schemes and geography require authoritative review.*/
        subject encounter;
        in attribute factsKnown : Boolean;
        in attribute channel : Boolean;
        in attribute ownSailing : Boolean;
        in attribute ownFishing : Boolean;
        in attribute otherConfined : Boolean;
        in attribute otherNavigatingChannel : Boolean;
        in attribute crossingChannel : Boolean;
        in attribute crossingImpede : Boolean;
        in attribute followingChannel : Boolean;
        in attribute safePracticableStarboardEdge : Boolean;
        in attribute nearObscuredBend : Boolean;
        in attribute caution : Boolean;
        in attribute bendSignal : Boolean;
        in attribute anchors : Boolean;
        in attribute avoidAnchoringPracticable : Boolean;
        in attribute tss : Boolean;
        in attribute usesLane : Boolean;
        in attribute followsFlow : Boolean;
        in attribute clearSeparation : Boolean;
        in attribute joinsLeaves : Boolean;
        in attribute atTermination : Boolean;
        in attribute smallJoinAngle : Boolean;
        in attribute crossesLane : Boolean;
        in attribute crossingAvoidable : Boolean;
        in attribute rightAngleHeading : Boolean;
        in attribute usesInshore : Boolean;
        in attribute canUseLane : Boolean;
        in attribute destinationException : Boolean;
        in attribute immediateDanger : Boolean;
        in attribute entersSeparationZone : Boolean;
        in attribute fishingInZone : Boolean;
        in attribute necessaryMaintenanceExemption : Boolean;
        in attribute necessaryCableExemption : Boolean;
        in attribute nearTermination : Boolean;
        in attribute terminationCaution : Boolean;
        in attribute wideAvoidanceMargin : Boolean;
        in attribute otherFollowingLane : Boolean;
        in attribute otherPower : Boolean;
        in attribute earlySeaRoom : Boolean;
        in attribute providedNonImpediment : Boolean;
        in attribute lengthM : Real;
        out attribute channelNonImpediment : Boolean = channel and (((ownSailing or lengthM < 20) and otherConfined) or (ownFishing and otherNavigatingChannel) or (crossingChannel and otherConfined));
        out attribute channelCrossingProhibited : Boolean = channel and crossingChannel and otherConfined and crossingImpede;
        out attribute channelBendSignalRequired : Boolean = channel and nearObscuredBend;
        out attribute channelAvoidAnchor : Boolean = channel and anchors and avoidAnchoringPracticable;
        out attribute channelSupported : Boolean = factsKnown and lengthM > 0 and not channelCrossingProhibited and not channelAvoidAnchor and (not (channel and followingChannel) or safePracticableStarboardEdge) and (not channelBendSignalRequired or (caution and bendSignal)) and (not channelNonImpediment or (earlySeaRoom and providedNonImpediment));
        out attribute limitedTssExemption : Boolean = necessaryMaintenanceExemption or necessaryCableExemption;
        out attribute inshorePermitted : Boolean = lengthM < 20 or ownSailing or ownFishing or not canUseLane or destinationException or immediateDanger;
        out attribute separationEntryPermitted : Boolean = crossesLane or joinsLeaves or immediateDanger or fishingInZone;
        out attribute tssNonImpediment : Boolean = tss and otherFollowingLane and (ownFishing or ((lengthM < 20 or ownSailing) and otherPower));
        out attribute ordinaryTssGeometrySupported : Boolean = (not usesLane or (followsFlow and clearSeparation and (not joinsLeaves or atTermination or smallJoinAngle))) and (not crossesLane or (not crossingAvoidable and rightAngleHeading)) and (not usesInshore or inshorePermitted) and (not entersSeparationZone or separationEntryPermitted) and (not nearTermination or terminationCaution) and (not anchors or not avoidAnchoringPracticable) and (usesLane or wideAvoidanceMargin);
        out attribute tssSupported : Boolean = factsKnown and lengthM > 0 and (not tss or ((ordinaryTssGeometrySupported or limitedTssExemption) and (not tssNonImpediment or (earlySeaRoom and providedNonImpediment))));
        out attribute exemptionScopeReviewRequired : Boolean = tss and limitedTssExemption;
        out attribute completeComplianceEstablished : Boolean = false;
    }
    analysis def RestrictedVisibility {
        doc /* Rule 19; no stand-on assignment is produced. Candidate restrictions use assessed relative geometry, radar-only acquisition and risk. Port/toward-target avoidance is treated conservatively without an automatic exception; any necessary departure needs separate Rule 2 assessment.*/
        subject encounter;
        in attribute factsKnown : Boolean;
        in attribute inSight : Boolean;
        in attribute inOrNearRestricted : Boolean;
        in attribute radarOnly : Boolean;
        in attribute forwardOfBeam : Boolean;
        in attribute abeamOrAbaft : Boolean;
        in attribute ownOvertaking : Boolean;
        in attribute portTurn : Boolean;
        in attribute towardTargetTurn : Boolean;
        in attribute courseAlteration : Boolean;
        in attribute closeQuarters : Boolean;
        in attribute fogSignalForward : Boolean;
        in attribute cannotAvoidForwardClose : Boolean;
        in attribute minimumSteerageSpeed : Boolean;
        in attribute allWayOffNecessary : Boolean;
        in attribute allWayOff : Boolean;
        in attribute extremeCaution : Boolean;
        in attribute enginePowered : Boolean;
        in attribute enginesReady : Boolean;
        in attribute earlyAvoidance : Boolean;
        in attribute safeSpeedAdapted : Boolean;
        in attribute risk : InlandExtended::Truth;
        out attribute applicable : Boolean = not inSight and inOrNearRestricted;
        out attribute avoidanceRequired : Boolean = applicable and radarOnly and (risk != Truth::no or closeQuarters);
        out attribute avoidPortTurn : Boolean = avoidanceRequired and courseAlteration and forwardOfBeam and not ownOvertaking;
        out attribute avoidTowardTarget : Boolean = avoidanceRequired and courseAlteration and abeamOrAbaft;
        out attribute minimumSpeedRequired : Boolean = applicable and risk != Truth::no and (fogSignalForward or cannotAvoidForwardClose);
        out attribute engineReadinessRequired : Boolean = applicable and enginePowered;
        out attribute candidateSupported : Boolean = factsKnown and (not applicable or (safeSpeedAdapted and (not engineReadinessRequired or enginesReady) and (not avoidanceRequired or earlyAvoidance) and (not avoidPortTurn or not portTurn) and (not avoidTowardTarget or not towardTargetTurn) and (not minimumSpeedRequired or (minimumSteerageSpeed and extremeCaution and (not allWayOffNecessary or allWayOff)))));
        out attribute completeComplianceEstablished : Boolean = false;
    }
    analysis def LightsAndShapes {
        doc /* Rules 20-31. Pattern obligations and size boundaries, not automatic image recognition. Outputs are simultaneous: ordinary/status/anchor/tow supplements must be combined by applicability. Specialized group tow layouts, fishing optional signals and approved alternatives are assessed separately. Rule 28 is reserved in Inland Rules; no constrained-by-draft privilege is invented.*/
        subject encounter;
        in attribute factsKnown : Boolean;
        in attribute night : Boolean;
        in attribute restrictedVisibility : Boolean;
        in attribute lightsCarried : Boolean;
        in attribute lightsDeemedNecessary : Boolean;
        in attribute makingWay : Boolean;
        in attribute underway : Boolean;
        in attribute anchored : Boolean;
        in attribute aground : Boolean;
        in attribute specialAnchorage : Boolean;
        in attribute awayFromNavigation : Boolean;
        in attribute sailAlsoPowered : Boolean;
        in attribute normalSailLightsPracticable : Boolean;
        in attribute chooseSmallSailAlternative : Boolean;
        in attribute chooseSmallPowerAlternative : Boolean;
        in attribute chooseSmallStatusExemption : Boolean;
        in attribute compositeUnit : Boolean;
        in attribute gearBeyond150m : Boolean;
        in attribute divingSmallDisplay : Boolean;
        in attribute obstruction : Boolean;
        in attribute gearRestrictedTowing : Boolean;
        in attribute partiallySubmerged : Boolean;
        in attribute towLightingImpracticable : Boolean;
        in attribute assistanceTow : Boolean;
        in attribute airActivity : Boolean;
        in attribute nonDisplacement : Boolean;
        in attribute mooredProjectsIntoChannel : Boolean;
        in attribute mooredWidthBelow80 : Boolean;
        in attribute groupMoreThanTwoWide : Boolean;
        in attribute groupWidthOver25 : Boolean;
        in attribute mooredParallel : Boolean;
        in attribute shelteredBargeExemption : Boolean;
        in attribute geographicBargeExemption : Boolean;
        in attribute allRequiredDisplaysPresent : Boolean;
        in attribute annexInstallationAccepted : Boolean;
        in attribute otherLightsNonConfusing : Boolean;
        in attribute mode : InlandExtended::Mode;
        in attribute lengthM : Real;
        in attribute towLengthM : Real;
        in attribute towBreadthM : Real;
        in attribute objectLengthM : Real;
        out attribute valid : Boolean = factsKnown and lengthM > 0 and towLengthM >= 0 and towBreadthM >= 0 and objectLengthM >= 0 and not (anchored and aground);
        out attribute displayLights : Boolean = night or (restrictedVisibility and lightsCarried) or lightsDeemedNecessary;
        out attribute displayShapes : Boolean = not night;
        out attribute smallSailAlternative : Boolean = not sailAlsoPowered and (mode == Mode::rowing or (mode == Mode::sail and lengthM < 7 and not normalSailLightsPracticable and chooseSmallSailAlternative));
        out attribute smallPowerAlternative : Boolean = (mode == Mode::power or sailAlsoPowered) and lengthM < 12 and chooseSmallPowerAlternative;
        out attribute smallStatusExemption : Boolean = lengthM < 12 and chooseSmallStatusExemption and mode != Mode::diving;
        out attribute anchorExemption : Boolean = anchored and ((lengthM < 7 and awayFromNavigation) or (lengthM < 20 and specialAnchorage));
        out attribute bargeLightsRequired : Boolean = mode == Mode::mooredBarge and not shelteredBargeExemption and not geographicBargeExemption and not (lengthM < 20 and specialAnchorage) and (mooredProjectsIntoChannel or mooredWidthBelow80 or groupMoreThanTwoWide or groupWidthOver25 or not mooredParallel);
        out attribute ordinaryUnderwayPattern : String = if smallSailAlternative ? "All-round white OR white torch/lantern displayed in time to prevent collision" else if (mode == Mode::sail or mode == Mode::rowing) and not sailAlsoPowered ? "Sidelights and sternlight; under 20 m combined masthead lantern is an option" else if smallPowerAlternative ? "All-round white and sidelights" else if lengthM >= 50 ? "Two masthead lights, sidelights and sternlight" else "Forward masthead, sidelights and sternlight";
        out attribute statusPattern : String = if mode == Mode::trawling ? "Green over white; two cones apexes together; aft higher masthead required at 50 m or more; sidelights/sternlight when making way" else if mode == Mode::fishing ? "Red over white; two cones apexes together; sidelights/sternlight when making way" else if mode == Mode::nuc ? (if smallStatusExemption ? "Rule 27 small-vessel display exemption selected" else "Two red all-round lights; two balls; sidelights/sternlight when making way") else if mode == Mode::ram or mode == Mode::dredging ? (if smallStatusExemption ? "Rule 27 small-vessel display exemption selected" else "Red-white-red all-round; ball-diamond-ball; power underway lights when making way") else if mode == Mode::diving ? (if divingSmallDisplay ? "Red-white-red all-round and rigid code flag A at least 1 m; all-round flag visibility" else "RAM display plus obstruction/passable-side displays when applicable") else if mode == Mode::mineClearance ? (if smallStatusExemption ? "Rule 27 small-vessel display exemption selected" else "Three green all-round lights or three balls in prescribed arrangement; dangerous within 1000 m") else if mode == Mode::pilot ? "White over red; sidelights/sternlight underway; anchor display at anchor" else "No additional status pattern";
        out attribute anchorPattern : String = if mode == Mode::fishing or mode == Mode::trawling ? "Rule 26 fishing display instead of anchor display" else if anchorExemption ? "Anchor display exemption applies" else if anchored or aground ? (if lengthM < 50 ? "One all-round white; anchor ball by day" else "Forward all-round white and lower aft white; anchor ball by day") else "No anchor display";
        out attribute groundingExtraRequired : Boolean = aground and lengthM >= 12;
        out attribute groundingExtraPattern : String = "If practicable: two red all-round lights and three balls";
        out attribute anchorDeckIlluminationRequired : Boolean = anchored and lengthM >= 100;
        out attribute sailMotorConeRequired : Boolean = sailAlsoPowered and lengthM >= 12;
        out attribute outlyingGearDisplayRequired : Boolean = mode == Mode::fishing and gearBeyond150m;
        out attribute outlyingGearPattern : String = "White all-round or cone apex upward toward gear";
        out attribute obstructionDisplayRequired : Boolean = (mode == Mode::dredging or mode == Mode::diving) and obstruction and not smallStatusExemption and not divingSmallDisplay;
        out attribute obstructionPattern : String = "Obstructed side: two red lights/two balls; passable side: two green lights/two diamonds; at anchor use these instead of Rule 30";
        out attribute airSupplement : String = if mode == Mode::airCushion and nonDisplacement ? "All-round flashing yellow" else if mode == Mode::wig and airActivity ? "High-intensity all-round flashing red" else "None";
        out attribute rule31ClosestPossibleRequired : Boolean = (mode == Mode::seaplane or mode == Mode::wig) and not allRequiredDisplaysPresent;
        out attribute rule28Reserved : Boolean = true;
        out attribute mastheadTowStackCount : Integer = if compositeUnit ? 0 else if mode == Mode::towingAstern ? (if towLengthM > 200 ? 3 else 2) else if mode == Mode::pushing ? 2 else 0;
        out attribute longTowDiamondRequired : Boolean = not compositeUnit and towLengthM > 200 and (mode == Mode::towingAstern or mode == Mode::towed);
        out attribute towPattern : String = if compositeUnit ? "Rule 23 power-driven composite unit" else if mode == Mode::towingAstern ? "Vertical masthead stack, sidelights, sternlight, yellow towing light above sternlight; Rule 23 masthead positioning applies" else if mode == Mode::pushing ? "Two masthead lights, sidelights, two towing lights; applicable river alternative requires review" else if mode == Mode::pushed ? "Forward sidelights and special flashing light" else if mode == Mode::towed and partiallySubmerged ? "White all-round outline lights and aft diamond" else if mode == Mode::towed ? "Sidelights and sternlight; alongside/group arrangements require review" else "No tow pattern";
        out attribute partialTowOutlineLightMinimum : Integer = if not partiallySubmerged ? 0 else if towBreadthM < 25 ? 2 else 4;
        out attribute partialTowIntermediateLightsRequired : Boolean = partiallySubmerged and objectLengthM > 100;
        out attribute partialTowMaxLightSpacingM : Real = 100;
        out attribute practicabilityAlternativeReviewRequired : Boolean = towLightingImpracticable or assistanceTow or rule31ClosestPossibleRequired;
        out attribute displayEvidenceSupported : Boolean = valid and allRequiredDisplaysPresent and annexInstallationAccepted and otherLightsNonConfusing and not practicabilityAlternativeReviewRequired;
        out attribute completeComplianceEstablished : Boolean = false;
        out attribute restrictedTowRamDisplayRequired : Boolean = gearRestrictedTowing and not smallStatusExemption;
        out attribute restrictedTowRamPattern : String = "In addition to Rule 24: red-white-red all-round and ball-diamond-ball";
    }
    analysis def Signals {
        doc /* Rules 32-37. Inland signal meanings differ from International maneuver signals. shortToleranceS is an explicit engineering interpretation of about one second. Signals are obligations/due events, not proof they were emitted or heard. Radio agreement removes only applicable passage-whistle duties, not danger/fog signals. Distress selection must be an authorized Annex IV signal; no transmitter is actuated.*/
        subject encounter;
        in attribute factsKnown : Boolean;
        in attribute inSight : Boolean;
        in attribute approaching : Boolean;
        in attribute powerPair : Boolean;
        in attribute underway : Boolean;
        in attribute meetingCrossing : Boolean;
        in attribute withinHalfMile : Boolean;
        in attribute overtaking : Boolean;
        in attribute intendLeaveOnPort : Boolean;
        in attribute intendOvertakeStarboard : Boolean;
        in attribute asternPropulsion : Boolean;
        in attribute passingAgreementReached : Boolean;
        in attribute otherProposalHeard : Boolean;
        in attribute proposalAccepted : Boolean;
        in attribute doubt : Boolean;
        in attribute bendOrObstruction : Boolean;
        in attribute heardBendSignal : Boolean;
        in attribute leavingBerth : Boolean;
        in attribute restrictedVisibility : Boolean;
        in attribute makingWay : Boolean;
        in attribute anchored : Boolean;
        in attribute aground : Boolean;
        in attribute mannedLastTow : Boolean;
        in attribute compositeUnit : Boolean;
        in attribute chooseSmallEfficientAlternative : Boolean;
        in attribute efficientSoundAvailable : Boolean;
        in attribute specialAnchorage : Boolean;
        in attribute pilotDuty : Boolean;
        in attribute distress : Boolean;
        in attribute assistanceRequired : Boolean;
        in attribute distressSignalChosen : Boolean;
        in attribute attentionNeeded : Boolean;
        in attribute attentionSignalNonConfusing : Boolean;
        in attribute attentionDoesNotDazzle : Boolean;
        in attribute signalEquipmentAccepted : Boolean;
        in attribute mode : InlandExtended::Mode;
        in attribute lengthM : Real;
        in attribute elapsedFogSignalS : Real;
        in attribute shortBlastS : Real;
        in attribute shortToleranceS : Real;
        in attribute prolongedBlastS : Real;
        out attribute whistleRequired : Boolean = lengthM >= 12;
        out attribute bellRequired : Boolean = lengthM >= 20;
        out attribute gongRequired : Boolean = lengthM >= 100;
        out attribute efficientSoundRequired : Boolean = lengthM < 12;
        out attribute blastDurationsSupported : Boolean = shortToleranceS >= 0 and shortBlastS >= 1-shortToleranceS and shortBlastS <= 1+shortToleranceS and prolongedBlastS >= 4 and prolongedBlastS <= 6;
        out attribute dangerSignalRequired : Boolean = inSight and approaching and doubt;
        out attribute dangerMinimumShortBlasts : Integer = if dangerSignalRequired ? 5 else 0;
        out attribute maneuverSignalRequired : Boolean = inSight and powerPair and underway and ((meetingCrossing and withinHalfMile) or overtaking) and not passingAgreementReached;
        out attribute maneuverShortBlasts : Integer = if not maneuverSignalRequired ? 0 else if asternPropulsion ? 3 else if overtaking ? (if intendOvertakeStarboard ? 1 else 2) else if intendLeaveOnPort ? 1 else 2;
        out attribute answerSameSignalRequired : Boolean = inSight and powerPair and otherProposalHeard and proposalAccepted and not passingAgreementReached;
        out attribute precautionUntilAgreementRequired : Boolean = inSight and powerPair and otherProposalHeard and not proposalAccepted;
        out attribute prolongedBendSignalRequired : Boolean = bendOrObstruction or heardBendSignal;
        out attribute prolongedDepartureSignalRequired : Boolean = leavingBerth and mode == Mode::power;
        out attribute smallFogAlternative : Boolean = chooseSmallEfficientAlternative and (lengthM < 12 or (lengthM < 20 and (anchored or aground)));
        out attribute fogAnchorExemption : Boolean = anchored and not aground and specialAnchorage and lengthM < 20 and mode != Mode::fishing and mode != Mode::trawling and not legallyRam;
        out attribute fogPattern : String = if not restrictedVisibility ? "None" else if fogAnchorExemption ? "Special anchorage exemption" else if smallFogAlternative ? "Other efficient sound" else if legallyRam or mode == Mode::fishing or mode == Mode::trawling ? "One prolonged then two short" else if aground ? "Anchor bell pattern plus three distinct strokes before and after; gong at 100 m" else if anchored ? "Rapid bell about 5 s; gong about 5 s after bell at 100 m" else if compositeUnit or mode == Mode::power or mode == Mode::pilot or mode == Mode::seaplane or mode == Mode::wig or mode == Mode::airCushion ? (if makingWay ? "One prolonged" else "Two prolonged separated by about 2 s") else if mode == Mode::towed and mannedLastTow ? "One prolonged then three short, after tug when practicable" else if mode == Mode::towed ? "No manned-tow signal duty" else "One prolonged then two short";
        out attribute fogSignalIntervalMaxS : Real = if not restrictedVisibility or fogAnchorExemption or (mode == Mode::towed and not mannedLastTow) ? 0 else if not smallFogAlternative and (anchored or aground) and not legallyRam and mode != Mode::fishing and mode != Mode::trawling ? 60 else 120;
        out attribute fogSignalDue : Boolean = fogSignalIntervalMaxS > 0 and elapsedFogSignalS >= fogSignalIntervalMaxS;
        out attribute pilotIdentityOptionalBlasts : Integer = if pilotDuty ? 4 else 0;
        out attribute distressSignalRequired : Boolean = distress and assistanceRequired;
        out attribute distressSignalMisuse : Boolean = distressSignalChosen and not distressSignalRequired;
        out attribute attentionSignalPermitted : Boolean = attentionNeeded and attentionSignalNonConfusing and attentionDoesNotDazzle;
        out attribute candidateSupported : Boolean = factsKnown and lengthM > 0 and elapsedFogSignalS >= 0 and blastDurationsSupported and signalEquipmentAccepted and (not efficientSoundRequired or efficientSoundAvailable) and (not smallFogAlternative or efficientSoundAvailable) and not distressSignalMisuse and (not distressSignalRequired or distressSignalChosen) and (not attentionNeeded or attentionSignalPermitted);
        out attribute completeComplianceEstablished : Boolean = false;
        out attribute legallyRam : Boolean = mode == Mode::ram or mode == Mode::dredging or mode == Mode::diving;
    }
    enum def LightKind {
        enum masthead;
        enum portSide;
        enum starboardSide;
        enum stern;
        enum towing;
        enum allRoundWhite;
        enum allRoundRed;
        enum allRoundGreen;
        enum specialFlashing;
        enum flashingYellow;
        enum flashingRed;
    }
    enum def Color {
        enum white;
        enum red;
        enum green;
        enum yellow;
    }
    analysis def LightFixture {
        doc /* Rules 21/22 and selected Annex I numerical demands. Color region checks are screening only; optical certification/evidence remains required. Red corner coordinates are ordered around their convex boundary, not read as a self-crossing polygon in table-column order. White uses the stated boundary order. This interpretation requires review against the incorporated CIE standard. Units: m, degrees, nautical miles, candela, flashes/minute.*/
        subject encounter;
        in attribute kind : InlandExtended::LightKind;
        in attribute lengthM : Real;
        in attribute nominalArcDeg : Real;
        in attribute measuredRangeNm : Real;
        in attribute minimumMeasuredIntensityCd : Real;
        in attribute colorX : Real;
        in attribute colorY : Real;
        in attribute flashesPerMinute : Real;
        in attribute factsKnown : Boolean;
        in attribute submergedTow : Boolean;
        in attribute unmannedBarge : Boolean;
        in attribute sailingUnderway : Boolean;
        in attribute horizontalSectorEvidenceAccepted : Boolean;
        in attribute verticalSectorEvidenceAccepted : Boolean;
        in attribute installationPositionEvidenceAccepted : Boolean;
        in attribute screensEvidenceAccepted : Boolean;
        out attribute requiredRangeNm : Real = if submergedTow ? 3 else if kind == LightKind::specialFlashing ? 2 else if kind == LightKind::masthead ? (if lengthM >= 50 ? 6 else if lengthM >= 20 ? 5 else if lengthM >= 12 ? 3 else 2) else if kind == LightKind::portSide or kind == LightKind::starboardSide ? (if lengthM >= 50 ? 3 else if lengthM >= 12 ? 2 else 1) else if lengthM >= 50 ? 3 else 2;
        out attribute requiredArcMinDeg : Real = if kind == LightKind::masthead ? 225 else if kind == LightKind::portSide or kind == LightKind::starboardSide ? 112.5 else if kind == LightKind::stern or kind == LightKind::towing ? 135 else if kind == LightKind::specialFlashing ? 180 else 360;
        out attribute requiredArcMaxDeg : Real = if kind == LightKind::specialFlashing ? 225 else requiredArcMinDeg;
        out attribute requiredColor : InlandExtended::Color = if kind == LightKind::portSide or kind == LightKind::allRoundRed or kind == LightKind::flashingRed ? Color::red else if kind == LightKind::starboardSide or kind == LightKind::allRoundGreen ? Color::green else if kind == LightKind::towing or kind == LightKind::specialFlashing or kind == LightKind::flashingYellow ? Color::yellow else Color::white;
        out attribute minimumIntensityCd : Real = if requiredRangeNm == 1 ? 0.686/0.8 else if requiredRangeNm == 2 ? 0.686*4/(0.8*0.8) else if requiredRangeNm == 3 ? 0.686*9/(0.8*0.8*0.8) else if requiredRangeNm == 5 ? 0.686*25/(0.8*0.8*0.8*0.8*0.8) else 0.686*36/(0.8*0.8*0.8*0.8*0.8*0.8);
        out attribute requiredVerticalOuterDeg : Real = if unmannedBarge ? 0 else if sailingUnderway ? 25 else 7.5;
        out attribute requiredOuterIntensityFraction : Real = if unmannedBarge ? 1 else if sailingUnderway ? 0.5 else 0.6;
        out attribute flashSupported : Boolean = if kind == LightKind::specialFlashing ? flashesPerMinute >= 50 and flashesPerMinute <= 70 else if kind == LightKind::flashingRed or kind == LightKind::flashingYellow ? flashesPerMinute >= 120 else true;
        out attribute whiteChromaticity : Boolean = (((((((0.382 > colorY) != (0.44 > colorY)) and colorX < (0.000000000)*(colorY-0.382)/(0.058000000)+0.525) != (((0.44 > colorY) != (0.348 > colorY)) and colorX < (-0.142000000)*(colorY-0.44)/(-0.092000000)+0.452)) != (((0.348 > colorY) != (0.283 > colorY)) and colorX < (0.000000000)*(colorY-0.348)/(-0.065000000)+0.31)) != (((0.283 > colorY) != (0.382 > colorY)) and colorX < (0.133000000)*(colorY-0.283)/(0.099000000)+0.31))) or (((0.000000000)*(colorY-0.382)-(0.058000000)*(colorX-0.525)) == 0 and colorX >= 0.525 and colorX <= 0.525 and colorY >= 0.382 and colorY <= 0.44) or (((-0.073000000)*(colorY-0.44)-(0.000000000)*(colorX-0.525)) == 0 and colorX >= 0.452 and colorX <= 0.525 and colorY >= 0.44 and colorY <= 0.44) or (((-0.142000000)*(colorY-0.44)-(-0.092000000)*(colorX-0.452)) == 0 and colorX >= 0.31 and colorX <= 0.452 and colorY >= 0.348 and colorY <= 0.44) or (((0.000000000)*(colorY-0.348)-(-0.065000000)*(colorX-0.31)) == 0 and colorX >= 0.31 and colorX <= 0.31 and colorY >= 0.283 and colorY <= 0.348) or (((0.133000000)*(colorY-0.283)-(0.099000000)*(colorX-0.31)) == 0 and colorX >= 0.31 and colorX <= 0.443 and colorY >= 0.283 and colorY <= 0.382) or (((0.082000000)*(colorY-0.382)-(0.000000000)*(colorX-0.443)) == 0 and colorX >= 0.443 and colorX <= 0.525 and colorY >= 0.382 and colorY <= 0.382);
        out attribute greenChromaticity : Boolean = (((((((0.385 > colorY) != (0.723 > colorY)) and colorX < (-0.019000000)*(colorY-0.385)/(0.338000000)+0.028) != (((0.723 > colorY) != (0.511 > colorY)) and colorX < (0.291000000)*(colorY-0.723)/(-0.212000000)+0.009)) != (((0.511 > colorY) != (0.356 > colorY)) and colorX < (-0.097000000)*(colorY-0.511)/(-0.155000000)+0.3)) != (((0.356 > colorY) != (0.385 > colorY)) and colorX < (-0.175000000)*(colorY-0.356)/(0.029000000)+0.203))) or (((-0.019000000)*(colorY-0.385)-(0.338000000)*(colorX-0.028)) == 0 and colorX >= 0.009 and colorX <= 0.028 and colorY >= 0.385 and colorY <= 0.723) or (((0.291000000)*(colorY-0.723)-(-0.212000000)*(colorX-0.009)) == 0 and colorX >= 0.009 and colorX <= 0.3 and colorY >= 0.511 and colorY <= 0.723) or (((-0.097000000)*(colorY-0.511)-(-0.155000000)*(colorX-0.3)) == 0 and colorX >= 0.203 and colorX <= 0.3 and colorY >= 0.356 and colorY <= 0.511) or (((-0.175000000)*(colorY-0.356)-(0.029000000)*(colorX-0.203)) == 0 and colorX >= 0.028 and colorX <= 0.203 and colorY >= 0.356 and colorY <= 0.385);
        out attribute redChromaticity : Boolean = ((-0.020000000)*(colorY-0.32)-(0.000000000)*(colorX-0.68)) >= 0 and ((0.061000000)*(colorY-0.32)-(-0.061000000)*(colorX-0.66)) >= 0 and ((0.014000000)*(colorY-0.259)-(0.006000000)*(colorX-0.721)) >= 0 and ((-0.055000000)*(colorY-0.265)-(0.055000000)*(colorX-0.735)) >= 0;
        out attribute yellowChromaticity : Boolean = ((((((0.382 > colorY) != (0.425 > colorY)) and colorX < (-0.043000000)*(colorY-0.382)/(0.043000000)+0.618) != (((0.425 > colorY) != (0.406 > colorY)) and colorX < (0.000000000)*(colorY-0.425)/(-0.019000000)+0.575)) != (((0.406 > colorY) != (0.382 > colorY)) and colorX < (0.037000000)*(colorY-0.406)/(-0.024000000)+0.575))) or (((0.006000000)*(colorY-0.382)-(0.000000000)*(colorX-0.612)) == 0 and colorX >= 0.612 and colorX <= 0.618 and colorY >= 0.382 and colorY <= 0.382) or (((-0.043000000)*(colorY-0.382)-(0.043000000)*(colorX-0.618)) == 0 and colorX >= 0.575 and colorX <= 0.618 and colorY >= 0.382 and colorY <= 0.425) or (((0.000000000)*(colorY-0.425)-(-0.019000000)*(colorX-0.575)) == 0 and colorX >= 0.575 and colorX <= 0.575 and colorY >= 0.406 and colorY <= 0.425) or (((0.037000000)*(colorY-0.406)-(-0.024000000)*(colorX-0.575)) == 0 and colorX >= 0.575 and colorX <= 0.612 and colorY >= 0.382 and colorY <= 0.406);
        out attribute chromaticitySupported : Boolean = if requiredColor == Color::white ? whiteChromaticity else if requiredColor == Color::red ? redChromaticity else if requiredColor == Color::green ? greenChromaticity else yellowChromaticity;
        out attribute fixtureSupported : Boolean = factsKnown and lengthM > 0 and nominalArcDeg >= requiredArcMinDeg and nominalArcDeg <= requiredArcMaxDeg and measuredRangeNm >= requiredRangeNm and minimumMeasuredIntensityCd >= minimumIntensityCd and chromaticitySupported and chromaticityEvidenceAccepted and flashSupported and horizontalSectorEvidenceAccepted and verticalSectorEvidenceAccepted and installationPositionEvidenceAccepted and screensEvidenceAccepted;
        out attribute completeComplianceEstablished : Boolean = false;
        in attribute chromaticityEvidenceAccepted : Boolean;
    }
    analysis def Installation {
        doc /* Annex I selected installation constraints. Special layouts/high-speed alternatives require reviewed drawings. Small commensurate shape sizes are externally assessed. Applicable hull/gunwale datum must be used. Does not certify every Annex I clause.*/
        subject encounter;
        in attribute lengthM : Real;
        in attribute breadthM : Real;
        in attribute mastheadHeightM : Real;
        in attribute mastheadAboveSidelightsM : Real;
        in attribute aftAboveForwardM : Real;
        in attribute verticalStackSpacingM : Real;
        in attribute lowestStackHeightM : Real;
        in attribute shapeDiameterM : Real;
        in attribute shapeHeightM : Real;
        in attribute shapeSpacingM : Real;
        in attribute forwardSectorCutoffDeg : Real;
        in attribute aftSectorCutoffDeg : Real;
        in attribute allRoundObscuredDeg : Real;
        in attribute factsKnown : Boolean;
        in attribute powered : Boolean;
        in attribute hasTwoMastheads : Boolean;
        in attribute hasVerticalStack : Boolean;
        in attribute towingStack : Boolean;
        in attribute threeLightsEquallySpaced : Boolean;
        in attribute smallShapeReductionAccepted : Boolean;
        in attribute shapeBlack : Boolean;
        in attribute coneOrDiamond : Boolean;
        in attribute anchorLight : Boolean;
        in attribute highSpeedAlternativeClaimed : Boolean;
        in attribute highSpeedAlternativeEvidenceAccepted : Boolean;
        in attribute horizontalPlacementAccepted : Boolean;
        in attribute trimVisibilityAccepted : Boolean;
        out attribute mastheadMinimumHeightM : Real = if lengthM >= 20 ? (if breadthM > 8 ? 8 else if breadthM > 5 ? breadthM else 5) else if lengthM >= 12 ? 2.5 else 0;
        out attribute mastheadHeightSupported : Boolean = not powered or ((not highSpeedAlternativeClaimed and mastheadHeightM >= mastheadMinimumHeightM) or (highSpeedAlternativeClaimed and highSpeedAlternativeEvidenceAccepted));
        out attribute sidelightSeparationSupported : Boolean = not powered or mastheadAboveSidelightsM >= 1;
        out attribute stackSupported : Boolean = not hasVerticalStack or (verticalStackSpacingM >= 1 and threeLightsEquallySpaced and (towingStack or lowestStackHeightM >= (if lengthM >= 20 ? 4 else 2)));
        out attribute shapeSupported : Boolean = shapeBlack and ((lengthM < 20 and smallShapeReductionAccepted) or (shapeDiameterM >= 0.6 and (not coneOrDiamond or shapeHeightM == shapeDiameterM) and shapeSpacingM >= 1.5));
        out attribute sectorCutoffSupported : Boolean = forwardSectorCutoffDeg >= 1 and forwardSectorCutoffDeg <= 3 and aftSectorCutoffDeg <= 5 and aftSectorCutoffDeg >= 0 and (anchorLight or allRoundObscuredDeg <= 6);
        out attribute installationSupported : Boolean = factsKnown and lengthM > 0 and breadthM > 0 and mastheadHeightSupported and sidelightSeparationSupported and stackSupported and shapeSupported and sectorCutoffSupported and (not hasTwoMastheads or aftAboveForwardM >= 2) and horizontalPlacementAccepted and trimVisibilityAccepted;
        out attribute completeComplianceEstablished : Boolean = false;
    }
    analysis def SoundAppliance {
        doc /* Annex III checks for a fitted whistle/bell. Small efficient alternatives are in Signals. Higher sound level is conservatively used at overlapping 450/800 Hz boundaries. Audibility range is not a detection guarantee; gong level needs separate measurement.*/
        subject encounter;
        in attribute lengthM : Real;
        in attribute fundamentalHz : Real;
        in attribute bandHz : Real;
        in attribute measuredBandDb : Real;
        in attribute forward45Db : Real;
        in attribute otherDirectionsDb : Real;
        in attribute listeningPostDb : Real;
        in attribute bellDb : Real;
        in attribute bellDiameterMm : Real;
        in attribute strikerMassFraction : Real;
        in attribute whistleSpacingM : Real;
        in attribute minimumFrequencyDifferenceHz : Real;
        in attribute conformingWhistleFraction : Real;
        in attribute factsKnown : Boolean;
        in attribute directional : Boolean;
        in attribute forwardAligned : Boolean;
        in attribute positioningReviewed : Boolean;
        in attribute combined : Boolean;
        in attribute twoWhistles : Boolean;
        in attribute higherFrequencyConforms : Boolean;
        in attribute simultaneous : Boolean;
        in attribute manualBell : Boolean;
        in attribute corrosionResistant : Boolean;
        in attribute clearTone : Boolean;
        in attribute bellFitted : Boolean;
        in attribute gongFitted : Boolean;
        in attribute gongDistinct : Boolean;
        out attribute minimumFundamentalHz : Real = if lengthM >= 200 ? 70 else if lengthM >= 75 ? 130 else 250;
        out attribute maximumFundamentalHz : Real = if lengthM >= 200 ? 200 else if lengthM >= 75 ? 350 else 700;
        out attribute minimumBandDb : Real = if lengthM >= 200 ? 143 else if lengthM >= 75 ? 138 else if lengthM >= 20 ? 130 else if bandHz <= 450 ? 120 else if bandHz <= 800 ? 115 else 111;
        out attribute bandValid : Boolean = bandHz >= 180*0.99 and bandHz <= (if lengthM >= 20 ? 700*1.01 else 2100*1.01);
        out attribute combinedSupported : Boolean = if combined ? whistleSpacingM <= 100 and simultaneous and minimumFrequencyDifferenceHz >= 10 and (if twoWhistles ? higherFrequencyConforms else conformingWhistleFraction >= 2.0/3.0) else whistleSpacingM <= 100 or not simultaneous;
        out attribute whistleSupported : Boolean = factsKnown and lengthM > 0 and fundamentalHz >= minimumFundamentalHz and fundamentalHz <= maximumFundamentalHz and bandValid and measuredBandDb >= minimumBandDb and forward45Db >= minimumBandDb-4 and otherDirectionsDb >= minimumBandDb-10 and listeningPostDb <= 110 and (not directional or forwardAligned) and positioningReviewed and combinedSupported;
        out attribute bellSupported : Boolean = not bellFitted or (bellDb >= 110 and (lengthM < 20 or bellDiameterMm >= 300) and strikerMassFraction >= 0.03 and manualBell and corrosionResistant and clearTone);
        out attribute lowerExposurePreferred : Boolean = listeningPostDb <= 100;
        out attribute equipmentSupported : Boolean = whistleSupported and bellSupported and (lengthM < 20 or bellFitted) and (lengthM < 100 or (gongFitted and gongDistinct));
        out attribute completeComplianceEstablished : Boolean = false;
    }
    analysis def ExemptionsAndSpecialCases {
        doc /* Rule 38, Rule 18(e/f), Annex IV/V, Parts 89/90. No new-build grandfathering or self-issued certificate. Geography is externally sourced. No supplemental light grants priority. Annex II/Part 85 and Inland Rule 28 are reserved.*/
        subject encounter;
        in attribute factsKnown : Boolean;
        in attribute constructedBefore19801224 : Boolean;
        in attribute legacyRulesSatisfied : Boolean;
        in attribute metricRepositionOnly : Boolean;
        in attribute certificateClaimed : Boolean;
        in attribute certificateIssued : Boolean;
        in attribute certificateStillApplicable : Boolean;
        in attribute certificateOnboard : Boolean;
        in attribute lawEnforcement : Boolean;
        in attribute publicSafetyAuthorized : Boolean;
        in attribute blueLightChosen : Boolean;
        in attribute redYellowChosen : Boolean;
        in attribute supplementalNonInterfering : Boolean;
        in attribute actualMechanicalRigidConnection : Boolean;
        in attribute movesAsOneVessel : Boolean;
        in attribute mooringBuoyFast : Boolean;
        in attribute specialRiverGeographyReviewed : Boolean;
        in attribute greatLakes : Boolean;
        in attribute westernRivers : Boolean;
        in attribute listed8925Water : Boolean;
        in attribute seaplaneOnWater : Boolean;
        in attribute wigFlight : Boolean;
        in attribute wigOnWater : Boolean;
        in attribute collisionRisk : Boolean;
        in attribute distress : Boolean;
        in attribute assistanceRequired : Boolean;
        in attribute authorizedAnnexIVSignal : Boolean;
        in attribute lengthM : Real;
        out attribute rule38Eligible : Boolean = constructedBefore19801224 and legacyRulesSatisfied;
        out attribute rule38RangeColorExemption : Boolean = rule38Eligible and lengthM < 20;
        out attribute rule38MetricRepositionExemption : Boolean = rule38Eligible and metricRepositionOnly;
        out attribute rule38HorizontalMastheadExemption : Boolean = rule38Eligible and lengthM < 150;
        out attribute rule38PowerLightAlternative : Boolean = rule38Eligible and lengthM >= 12 and lengthM < 20;
        out attribute alternativeCertificateSupported : Boolean = certificateClaimed and certificateIssued and certificateStillApplicable and certificateOnboard;
        out attribute blueLightPermitted : Boolean = lawEnforcement and supplementalNonInterfering;
        out attribute redYellowPermitted : Boolean = publicSafetyAuthorized and supplementalNonInterfering;
        out attribute supplementalPriorityGranted : Boolean = false;
        out attribute compositeUnit : Boolean = actualMechanicalRigidConnection and movesAsOneVessel;
        out attribute anchorRulesApplyToMooring : Boolean = mooringBuoyFast;
        out attribute specialRiverRulesApply : Boolean = specialRiverGeographyReviewed and (greatLakes or westernRivers or listed8925Water);
        out attribute seaplaneGeneralKeepClear : Boolean = seaplaneOnWater;
        out attribute wigFlightKeepClear : Boolean = wigFlight;
        out attribute wigSurfacePowerRules : Boolean = wigOnWater;
        out attribute seaplaneEncounterRulesAlsoApply : Boolean = seaplaneOnWater and collisionRisk;
        out attribute distressUseSupported : Boolean = not authorizedAnnexIVSignal or (distress and assistanceRequired);
        out attribute assessmentSupported : Boolean = factsKnown and lengthM > 0 and (not certificateClaimed or alternativeCertificateSupported) and (not blueLightChosen or blueLightPermitted) and (not redYellowChosen or redYellowPermitted) and distressUseSupported;
        out attribute completeComplianceEstablished : Boolean = false;
    }
    analysis def CandidateAssessment {
        doc /* Combines independently evaluated domains for one consistent candidate and observation. Caller supplies native outputs, not manually invented pass flags. No complete compliance verdict. Nonvisual clear-weather contacts remain unsupported for automatic role selection. Multiple fixture/installations must be checked externally; inputs here are their aggregate evidence results.*/
        subject encounter;
        in attribute factsConsistent : Boolean;
        in attribute inSight : Boolean;
        in attribute inOrNearRestricted : Boolean;
        in attribute generalSupported : Boolean;
        in attribute pairwiseSupported : Boolean;
        in attribute restrictedVisibilitySupported : Boolean;
        in attribute channelSupported : Boolean;
        in attribute tssSupported : Boolean;
        in attribute signalsSupported : Boolean;
        in attribute displaySupported : Boolean;
        in attribute fixturesSupported : Boolean;
        in attribute installationSupported : Boolean;
        in attribute soundSupported : Boolean;
        in attribute specialCasesSupported : Boolean;
        in attribute additionalApplicableClausesReviewed : Boolean;
        out attribute candidateSupported : Boolean = factsConsistent and generalSupported and (if inSight ? pairwiseSupported else inOrNearRestricted and restrictedVisibilitySupported) and channelSupported and tssSupported and signalsSupported and displaySupported and fixturesSupported and installationSupported and soundSupported and specialCasesSupported and specialDisplaysSupported and passageProtocolSupported and distressCatalogSupported and additionalApplicableClausesReviewed;
        out attribute completeComplianceEstablished : Boolean = false;
        in attribute specialDisplaysSupported : Boolean;
        in attribute passageProtocolSupported : Boolean;
        in attribute distressCatalogSupported : Boolean;
    }
    analysis def SnapshotConsistency {
        doc /* Reject inconsistent shared facts across independently evaluated domains. This checks representation consistency, not truth or sufficient sensor evidence. All frames must identify the same vessel, encounter, time and candidate externally.*/
        subject encounter;
        in attribute coreLengthM : Real;
        in attribute channelLengthM : Real;
        in attribute lightLengthM : Real;
        in attribute fixtureLengthM : Real;
        in attribute installationLengthM : Real;
        in attribute soundLengthM : Real;
        in attribute signalLengthM : Real;
        in attribute specialLengthM : Real;
        in attribute coreSight : InlandExtended::Truth;
        in attribute coreRisk : InlandExtended::Truth;
        in attribute generalRisk : InlandExtended::Truth;
        in attribute visibilityRisk : InlandExtended::Truth;
        in attribute coreChannel : InlandExtended::Truth;
        in attribute coreConfined : InlandExtended::Truth;
        in attribute coreCrossing : InlandExtended::Truth;
        in attribute coreNavigatingChannel : InlandExtended::Truth;
        in attribute visibilitySight : Boolean;
        in attribute signalSight : Boolean;
        in attribute channel : Boolean;
        in attribute confined : Boolean;
        in attribute crossing : Boolean;
        in attribute navigatingChannel : Boolean;
        in attribute sailAlsoPowered : Boolean;
        in attribute coreKind : String;
        in attribute lightMode : String;
        in attribute signalMode : String;
        out attribute lengthsAgree : Boolean = coreLengthM > 0 and coreLengthM == channelLengthM and coreLengthM == lightLengthM and coreLengthM == fixtureLengthM and coreLengthM == installationLengthM and coreLengthM == soundLengthM and coreLengthM == signalLengthM and coreLengthM == specialLengthM;
        out attribute sightAgrees : Boolean = coreSight != Truth::unknown and (coreSight == Truth::yes) == visibilitySight and visibilitySight == signalSight;
        out attribute channelAgrees : Boolean = coreChannel != Truth::unknown and (coreChannel == Truth::yes) == channel and coreConfined != Truth::unknown and (coreConfined == Truth::yes) == confined and coreCrossing != Truth::unknown and (coreCrossing == Truth::yes) == crossing and coreNavigatingChannel != Truth::unknown and (coreNavigatingChannel == Truth::yes) == navigatingChannel;
        out attribute modeAgrees : Boolean = (if lightMode == "sail" and sailAlsoPowered ? signalMode == "power" else lightMode == signalMode) and ((coreKind == "sailing" and lightMode == "sail" and not sailAlsoPowered) or (coreKind == "power" and (lightMode == "power" or (lightMode == "sail" and sailAlsoPowered))) or (coreKind == "fishing" and (lightMode == "fishing" or lightMode == "trawling")) or (coreKind == "notUnderCommand" and lightMode == "nuc") or (coreKind == "restrictedManeuverability" and (lightMode == "ram" or lightMode == "dredging" or lightMode == "diving")));
        out attribute consistent : Boolean = lengthsAgree and sightAgrees and channelAgrees and modeAgrees and passageAgrees and coreRisk == generalRisk and coreRisk == visibilityRisk and (not generalRiskPresent or coreRisk != Truth::no) and coreRestricted != Truth::unknown and (coreRestricted == Truth::yes) == lightRestricted and lightRestricted == signalRestricted and signalRestricted == visibilityRestricted;
        out attribute completeComplianceEstablished : Boolean = false;
        in attribute generalRiskPresent : Boolean;
        in attribute lightRestricted : Boolean;
        in attribute signalRestricted : Boolean;
        in attribute visibilityRestricted : Boolean;
        in attribute coreRestricted : InlandExtended::Truth;
        in attribute signalExchangeRequired : Boolean;
        in attribute protocolExchangeRequired : Boolean;
        in attribute signalAgreement : Boolean;
        in attribute protocolAgreement : Boolean;
        in attribute coreAgreement : String;
        out attribute passageAgrees : Boolean = (not signalExchangeRequired or protocolExchangeRequired) and signalAgreement == protocolAgreement and (not (coreAgreement == "portToPort" or coreAgreement == "starboardToStarboard") or protocolAgreement);
    }
    analysis def SpecialDisplays {
        doc /* Conditional alternatives/supplements in Rules20,23-27,30-31. Optional fishing lights must be lower and less visible than principal fishing lights. Dimensions, exact geographic applicability and practicability are externally assessed. Outputs are simultaneous applicable pattern supplements, not automatic hardware commands.*/
        subject encounter;
        in attribute factsKnown : Boolean;
        in attribute greatLakes : Boolean;
        in attribute useGreatLakesPowerAlternative : Boolean;
        in attribute regionalPushAlternativeApplicable : Boolean;
        in attribute chooseRegionalPushAlternative : Boolean;
        in attribute combinedSailingLantern : Boolean;
        in attribute optionalRedOverGreen : Boolean;
        in attribute fishingCloseProximity : Boolean;
        in attribute shootingNets : Boolean;
        in attribute haulingNets : Boolean;
        in attribute netFast : Boolean;
        in attribute pairTrawling : Boolean;
        in attribute purseSeine : Boolean;
        in attribute hamperedByGear : Boolean;
        in attribute pushedAhead : Boolean;
        in attribute towedAlongside : Boolean;
        in attribute alongsideBothSides : Boolean;
        in attribute groupTow : Boolean;
        in attribute towImpracticable : Boolean;
        in attribute assistanceTow : Boolean;
        in attribute unableToTowDisplay : Boolean;
        in attribute allPossibleTowIndication : Boolean;
        in attribute bridgePassageLoweringNecessary : Boolean;
        in attribute anchorCornerAlternative : Boolean;
        in attribute mooredBothSides : Boolean;
        in attribute projectingBarge : Boolean;
        in attribute specialBargeExemptionReviewed : Boolean;
        in attribute specialBargeExemption : Boolean;
        in attribute seaplaneFullDisplayImpossible : Boolean;
        in attribute closestPossibleArrangementReviewed : Boolean;
        in attribute optionalFishingSpacingAccepted : Boolean;
        in attribute mode : InlandExtended::Mode;
        in attribute lengthM : Real;
        out attribute greatLakesAlternativeAvailable : Boolean = greatLakes and mode == Mode::power;
        out attribute greatLakesAlternativePattern : String = "All-round white at second masthead position replaces second masthead and sternlight; same minimum range";
        out attribute regionalPushPattern : String = "Sidelights and two towing lights; no masthead lights under applicable regional provision";
        out attribute sailingOptionalPatternPermitted : Boolean = mode == Mode::sail and not combinedSailingLantern;
        out attribute fishingOptionalPattern : String = if not fishingCloseProximity ? "None" else if purseSeine and hamperedByGear ? "Two yellow lights alternate each second, equal light/dark duration" else if mode == Mode::trawling and shootingNets ? "Two white all-round lights vertically" else if mode == Mode::trawling and haulingNets ? "White over red all-round" else if mode == Mode::trawling and netFast ? "Two red all-round lights vertically" else "None";
        out attribute pairTrawlSearchlightOptional : Boolean = fishingCloseProximity and pairTrawling and mode == Mode::trawling;
        out attribute optionalFishingRangeNm : Real = 1;
        out attribute optionalFishingMinSpacingM : Real = 0.9;
        out attribute groupTowPattern : String = if alongsideBothSides ? "Each outboard stern light; one set of forward/outboard sidelights; one special flashing light" else if towedAlongside ? "Sternlight plus forward sidelights and special flashing light" else if pushedAhead ? "Forward sidelights and special flashing light" else if groupTow ? "Treat group as one vessel except both-side alongside arrangement" else "None";
        out attribute bargeCornerPattern : String = if not anchorCornerAlternative ? "Ordinary Rule30 pattern" else if projectingBarge ? "Mark projecting outboard corners" else if mooredBothSides ? "Mark single/group corner extremities" else "Arrangement applicability review";
        out attribute bargeAlternativeRangeNm : Real = 1;
        out attribute bridgeLoweringPermitted : Boolean = bridgePassageLoweringNecessary;
        out attribute displayAlternativeSupported : Boolean = factsKnown and lengthM > 0 and (not useGreatLakesPowerAlternative or greatLakesAlternativeAvailable) and (not chooseRegionalPushAlternative or (regionalPushAlternativeApplicable and mode == Mode::pushing)) and (not optionalRedOverGreen or sailingOptionalPatternPermitted) and (not (towImpracticable or (assistanceTow and unableToTowDisplay)) or allPossibleTowIndication) and (not seaplaneFullDisplayImpossible or closestPossibleArrangementReviewed) and (not specialBargeExemption or specialBargeExemptionReviewed) and (not fishingCloseProximity or optionalFishingSpacingAccepted);
        out attribute completeComplianceEstablished : Boolean = false;
    }
    analysis def PassageProtocol {
        doc /* Rule34 and special river proposal/holding duties. priorAgreement belongs to this same pair and proposed maneuver; expiry/change must clear it. Planned passage protocol does not veto necessary emergency action. Whistle/radio emission and reception are measured inputs.*/
        subject encounter;
        in attribute factsKnown : Boolean;
        in attribute requiredExchange : Boolean;
        in attribute proposalSent : Boolean;
        in attribute proposalReceived : Boolean;
        in attribute ownAgreement : Boolean;
        in attribute otherAgreement : Boolean;
        in attribute doubt : Boolean;
        in attribute maneuverStarted : Boolean;
        in attribute radioAgreement : Boolean;
        in attribute lawfulAlternative : Boolean;
        in attribute riskResolved : Boolean;
        in attribute downboundWithCurrent : Boolean;
        in attribute specialRiverPriority : Boolean;
        in attribute upboundOpposite : Boolean;
        in attribute holdingForPassage : Boolean;
        in attribute mannerAndPlaceProposed : Boolean;
        in attribute signalInitiated : Boolean;
        in attribute bridgePassageComplete : Boolean;
        in attribute loweredLightsRestored : Boolean;
        in attribute priorAgreement : InlandExtended::Truth;
        out attribute currentAgreement : Boolean = factsKnown and not doubt and (radioAgreement or (ownAgreement and otherAgreement and proposalSent and proposalReceived) or priorAgreement == Truth::yes);
        out attribute dangerSignalRequired : Boolean = doubt;
        out attribute precautionRequired : Boolean = requiredExchange and not currentAgreement;
        out attribute proposalRequired : Boolean = specialRiverPriority and downboundWithCurrent;
        out attribute holdRequired : Boolean = specialRiverPriority and upboundOpposite;
        out attribute protocolSupported : Boolean = factsKnown and (not (maneuverStarted and requiredExchange) or currentAgreement or riskResolved) and (not lawfulAlternative or currentAgreement) and (not proposalRequired or (mannerAndPlaceProposed and signalInitiated)) and (not holdRequired or holdingForPassage) and (not bridgePassageComplete or loweredLightsRestored);
        out attribute agreementRetained : Boolean = currentAgreement and not riskResolved;
        out attribute completeComplianceEstablished : Boolean = false;
    }
    analysis def DistressCatalog {
        doc /* Rule37 / Annex IV catalog. No transmitter or pyrotechnic is actuated. Supplemental canvas/dye cannot replace a required recognized distress signal. Detailed radio coding/channel and emission characteristics require protocol evidence.*/
        subject encounter;
        in attribute signalName : String;
        in attribute factsKnown : Boolean;
        in attribute distress : Boolean;
        in attribute assistanceRequired : Boolean;
        in attribute chosen : Boolean;
        in attribute authorizedRadioEquipment : Boolean;
        in attribute supplementalOnly : Boolean;
        in attribute whiteFlashesPerMinute : Real;
        out attribute listedAnnexIVSignal : Boolean = signalName == "minuteExplosive" or signalName == "continuousFog" or signalName == "redStars" or signalName == "SOS" or signalName == "Mayday" or signalName == "NC" or signalName == "squareFlagBall" or signalName == "flames" or signalName == "redFlare" or signalName == "orangeSmoke" or signalName == "raisedArms" or signalName == "DSC" or signalName == "satelliteDistress" or signalName == "EPIRB" or signalName == "survivalRadio" or (signalName == "highIntensityWhite" and whiteFlashesPerMinute >= 50 and whiteFlashesPerMinute <= 70);
        out attribute radioSignal : Boolean = signalName == "Mayday" or signalName == "DSC" or signalName == "satelliteDistress" or signalName == "EPIRB" or signalName == "survivalRadio";
        out attribute supplementalAid : Boolean = signalName == "orangeCanvas" or signalName == "dyeMarker";
        out attribute useSupported : Boolean = factsKnown and (not chosen or (distress and assistanceRequired and ((listedAnnexIVSignal and (not radioSignal or authorizedRadioEquipment)) or (supplementalOnly and supplementalAid))));
        out attribute completeComplianceEstablished : Boolean = false;
    }
}

package InlandNavigationExperiment {
    doc /* Reusable U.S. Inland Rules interpretation. Supplied facts and candidate checks are conditional assessments, not established legal compliance. The mission navigation adapter consumes the pair assessment; equipment and other obligations remain separately assessed.*/
    private import ScalarValues::*;
    enum def Truth { yes; no; unknown; }
    enum def VesselKind { sailing; power; unclassified;
        enum fishing;
        enum notUnderCommand;
        enum restrictedManeuverability;
    }
    enum def Tack { portTack; starboardTack; unresolved; }
    enum def Windward { ownWindward; otherWindward; unresolved; }
    enum def OvertakingMemory { clear; ownDuty; otherDuty; conflicting; }
    enum def EncounterRole { giveWay; standOn; noPairRole; unsupported;
        enum mutualAvoidance;
    }
    enum def Response { monitor; keepClear; holdCourseSpeed; mayAct; shallAct; unresolved; }
    part context;
    analysis def Assess {
        doc /* One stable pair identity at one observation. Call repeatedly with nextMemory from the preceding result; preserve memory on uncertain clearance. Changing vessel identity requires explicit caller reset. Rule 13 memory, Rule 12 roles, Rule 17 escalation and Rule 9 obligations remain distinct. No turn command, CPA threshold, safe-speed calculation or observation classifier is implemented.*/
        subject encounter;
        in attribute inlandProfile : Truth;
        in attribute inSight : Truth {
            doc /* Rule 3(k) visual observability assessed externally. AIS/radar acquisition alone is not sufficient.*/
        }
        in attribute restrictedVisibility : Truth;
        in attribute riskOfCollision : Truth {
            doc /* Rule 7 risk appraisal supplied externally; unknown is treated as risk, not a CPA-based clearance claim.*/
        }
        in attribute ownKind : VesselKind;
        in attribute otherKind : VesselKind;
        in attribute ownExceptionalStatus : Truth {
            doc /* Unresolved or additional status not represented by VesselKind; known fishing, NUC and RAM are now typed VesselKind values. Do not infer status from size or automation.*/
        }
        in attribute otherExceptionalStatus : Truth;
        in attribute unmodeledSpecialCircumstances : Truth {
            doc /* Includes traffic separation, special inland river priority, agreed passages, multi-vessel interactions and Rule 2 circumstances requiring interpretation outside this subset.*/
        }
        in attribute observationsAdequate : Truth;
        in attribute lookoutAdequate : Truth;
        in attribute safeSpeedSupported : Truth;
        in attribute ownTack : Tack;
        in attribute otherTack : Tack;
        in attribute windward : Windward;
        in attribute ownComingUp : Truth;
        in attribute otherComingUp : Truth;
        in attribute ownBearingLowDeg : Real {
            doc /* Lower folded absolute bearing of ownship as seen from the OTHER vessel, measured from its bow, 0..180 degrees; not ownship bearing to target.*/
        }
        in attribute ownBearingHighDeg : Real;
        in attribute otherBearingLowDeg : Real {
            doc /* Lower folded absolute bearing of target as seen from OWNSHIP bow, 0..180 degrees.*/
        }
        in attribute otherBearingHighDeg : Real;
        in attribute declaredOwnOvertakingDoubt : Truth {
            doc /* Independent doubt about being the overtaker. Unknown is treated as unresolved doubt for this experiment; distinguish from known not-overtaking.*/
        }
        in attribute previousMemory : OvertakingMemory {
            doc /* State supplied by caller for this same pair. Native outputs compute the transition; Python only transports it.*/
        }
        in attribute pastAndClear : Truth {
            doc /* Positive evidence that this encounter is finally past and clear; unknown cannot release an overtaking duty.*/
        }
        in attribute otherActionAppropriate : Truth {
            doc /* No means it has become apparent that the give-way vessel is not taking appropriate action; no timer is invented.*/
        }
        in attribute giveWayAloneSufficient : Truth {
            doc /* No means collision cannot be avoided by give-way action alone (Rule 17(b)); unknown does not establish that threshold.*/
        }
        in attribute ownAvoidanceFeasible : Truth;
        in attribute immediateDanger : Truth;
        in attribute channelContext : Truth {
            doc /* Includes approach/crossing of an applicable narrow channel, not only ownship physically inside it.*/
        }
        in attribute otherConfinedToChannel : Truth;
        in attribute ownLengthM : Real;
        in attribute crossingChannel : Truth;
        in attribute crossingWouldImpede : Truth;
        in attribute proceedingAlongChannel : Truth;
        in attribute channelPlanSupported : Truth {
            doc /* External review of practicable starboard-edge navigation, sufficient sea room, signaling and nonimpediment. Not implied by pair role.*/
        }
        out attribute inputBoundsValid : Boolean = ownLengthM > 0 and ownBearingLowDeg >= 0 and ownBearingHighDeg <= 180 and ownBearingLowDeg <= ownBearingHighDeg and otherBearingLowDeg >= 0 and otherBearingHighDeg <= 180 and otherBearingLowDeg <= otherBearingHighDeg {
            doc /* Engineering input contract, not a legal threshold.*/
        }
        out attribute clearanceConflict : Boolean = pastAndClear == Truth::yes and (riskOfCollision != Truth::no or clearanceEvidenceAdequate != Truth::yes) {
            doc /* Engineering consistency check: positive clearance requires adequate independent clearance evidence and a no-risk appraisal before releasing memory.*/
        }
        out attribute riskDeemedPresent : Boolean = riskOfCollision != Truth::no {
            doc /* Rule 7(a): doubt does not establish absence of collision risk.*/
        }
        out attribute ownOvertakingConfirmed : Boolean = inputBoundsValid and ownComingUp == Truth::yes and ownBearingLowDeg > 112.5 {
            doc /* Rule 13(b): 22.5 degrees abaft beam equals 112.5 from bow; strict greater-than.*/
        }
        out attribute ownOvertakingPresumed : Boolean = inputBoundsValid and not ownOvertakingConfirmed and (declaredOwnOvertakingDoubt != Truth::no or (ownComingUp != Truth::no and ownBearingHighDeg > 112.5)) {
            doc /* Rule 13(c) plus engineering interval interpretation: possible overtaking triggers own-duty presumption.*/
        }
        out attribute otherOvertakingConfirmed : Boolean = inputBoundsValid and otherComingUp == Truth::yes and otherBearingLowDeg > 112.5 {
            doc /* Confirmed other-overtaker geometry; uncertainty alone never awards stand-on status.*/
        }
        out attribute otherOvertakingUncertain : Boolean = inputBoundsValid and not otherOvertakingConfirmed and otherComingUp != Truth::no and otherBearingHighDeg > 112.5;
        out attribute ownDutyCandidate : Boolean = previousMemory == OvertakingMemory::ownDuty or ownOvertakingConfirmed or ownOvertakingPresumed;
        out attribute otherDutyCandidate : Boolean = previousMemory == OvertakingMemory::otherDuty or otherOvertakingConfirmed;
        out attribute pairwiseScopeSupported : Boolean = inputBoundsValid and not clearanceConflict and inlandProfile == Truth::yes and inSight == Truth::yes and observationsAdequate == Truth::yes and ownKind != VesselKind::unclassified and otherKind != VesselKind::unclassified and ownExceptionalStatus == Truth::no and otherExceptionalStatus == Truth::no and unmodeledSpecialCircumstances == Truth::no {
            doc /* Conservative experiment scope. Unsupported is not permission to ignore obligations.*/
        }
        out attribute nextMemory : OvertakingMemory = if not inputBoundsValid or clearanceConflict ? previousMemory else if pastAndClear == Truth::yes ? OvertakingMemory::clear else if not pairwiseScopeSupported ? previousMemory else if previousMemory == OvertakingMemory::conflicting or (ownDutyCandidate and otherDutyCandidate) ? OvertakingMemory::conflicting else if ownDutyCandidate ? OvertakingMemory::ownDuty else if otherDutyCandidate ? OvertakingMemory::otherDuty else OvertakingMemory::clear {
            doc /* Rule 13(d). Preserve established duty on lost sight/unknown status; do not acquire new memory from inadequate observations. Conflicting identity/geometry remains unresolved until clearance/reset.*/
        }
        out attribute sailingRole : EncounterRole = if ownKind != VesselKind::sailing or otherKind != VesselKind::sailing ? EncounterRole::unsupported else if ownTack == Tack::portTack and otherTack == Tack::starboardTack ? EncounterRole::giveWay else if ownTack == Tack::starboardTack and otherTack == Tack::portTack ? EncounterRole::standOn else if ownTack == Tack::portTack and otherTack == Tack::unresolved and windward == Windward::otherWindward ? EncounterRole::giveWay else if ownTack != Tack::unresolved and ownTack == otherTack and windward == Windward::ownWindward ? EncounterRole::giveWay else if ownTack != Tack::unresolved and ownTack == otherTack and windward == Windward::otherWindward ? EncounterRole::standOn else EncounterRole::unsupported {
            doc /* Rule 12. Tack and windward side are supplied legal interpretations, not deduced from a kite or symmetric wing.*/
        }
        out attribute role : EncounterRole = if not pairwiseScopeSupported ? EncounterRole::unsupported else if pastAndClear == Truth::yes ? EncounterRole::noPairRole else if nextMemory == OvertakingMemory::conflicting ? EncounterRole::unsupported else if nextMemory == OvertakingMemory::ownDuty ? EncounterRole::giveWay else if nextMemory == OvertakingMemory::otherDuty ? EncounterRole::standOn else if otherOvertakingUncertain ? EncounterRole::unsupported else if not riskDeemedPresent ? EncounterRole::noPairRole else ordinaryRole {
            doc /* Rule 13 takes priority over sailing role. Low current collision risk does not erase active overtaking duty.*/
        }
        out attribute ruleBasis : String = if not pairwiseScopeSupported ? "Insufficient assessed facts or special circumstances" else if nextMemory == OvertakingMemory::ownDuty or nextMemory == OvertakingMemory::otherDuty ? "Rule 13 persistent overtaking" else if not riskDeemedPresent ? "No pair risk reported; general duties remain" else if riverRole != EncounterRole::noPairRole ? "Rules 9/14/15 special inland river provisions" else if ownRule18GiveWay or otherRule18GiveWay ? "Rule 18; channel/TSS obligations independently apply" else if headOnPresumed ? "Rule 14 head-on" else if powerPair and powerEncounter == PowerEncounter::crossing ? "Rule 15 crossing" else "Rule 12 or unresolved encounter";
        out attribute response : Response = if role == EncounterRole::unsupported ? Response::unresolved else if role == EncounterRole::giveWay or role == EncounterRole::mutualAvoidance ? Response::keepClear else if role == EncounterRole::noPairRole ? Response::monitor else if giveWayAloneSufficient == Truth::no ? Response::shallAct else if otherActionAppropriate == Truth::no ? Response::mayAct else if giveWayAloneSufficient == Truth::unknown or otherActionAppropriate == Truth::unknown ? Response::unresolved else Response::holdCourseSpeed {
            doc /* Rules 16/17: optional action and mandatory action are distinct. Emergency review reports need for broader Rule 2 judgment, not permission for arbitrary departure.*/
        }
        out attribute nonImpedimentDuty : Truth = if inlandProfile != Truth::yes or not inputBoundsValid or ownExceptionalStatus != Truth::no or unmodeledSpecialCircumstances != Truth::no ? Truth::unknown else if channelContext == Truth::no ? Truth::no else if channelContext == Truth::unknown ? Truth::unknown else if ownKind == VesselKind::fishing and otherNavigatingChannel == Truth::yes ? Truth::yes else if ownKind == VesselKind::fishing and otherNavigatingChannel == Truth::unknown ? Truth::unknown else if otherConfinedToChannel == Truth::no ? Truth::no else if otherConfinedToChannel == Truth::unknown ? Truth::unknown else if ownLengthM < 20 or ownKind == VesselKind::sailing or crossingChannel == Truth::yes ? Truth::yes else if ownKind == VesselKind::unclassified or crossingChannel == Truth::unknown ? Truth::unknown else Truth::no {
            doc /* Rules 9(b/c/d), independent of pairwise role and instantaneous collision risk. Typed fishing status carries duty toward any vessel navigating the channel, not only channel-confined vessels.*/
        }
        out attribute crossingProhibited : Truth = if inlandProfile != Truth::yes or not inputBoundsValid ? Truth::unknown else if channelContext == Truth::no or crossingChannel == Truth::no or otherConfinedToChannel == Truth::no or crossingWouldImpede == Truth::no ? Truth::no else if channelContext == Truth::yes and crossingChannel == Truth::yes and otherConfinedToChannel == Truth::yes and crossingWouldImpede == Truth::yes ? Truth::yes else Truth::unknown {
            doc /* Rule 9(d); prohibited only when the assessed crossing impedes confined passage. Unknown is not permission to cross.*/
        }
        out attribute starboardEdgeDuty : Truth = if inlandProfile != Truth::yes or unmodeledSpecialCircumstances != Truth::no ? Truth::unknown else if channelContext == Truth::no or proceedingAlongChannel == Truth::no ? Truth::no else if channelContext == Truth::yes and proceedingAlongChannel == Truth::yes ? Truth::yes else Truth::unknown {
            doc /* Rule 9(a)(i): as near as safe and practicable. No geometric edge offset is invented.*/
        }
        out attribute channelObligationsSupported : Boolean = nonImpedimentDuty != Truth::unknown and crossingProhibited == Truth::no and starboardEdgeDuty != Truth::unknown and ((nonImpedimentDuty == Truth::no and starboardEdgeDuty == Truth::no) or channelPlanSupported == Truth::yes) {
            doc /* Engineering readiness check; nonimpediment remains separate and is not erased by stand-on status.*/
        }
        out attribute rule19AssessmentNeeded : Boolean = inSight != Truth::yes and restrictedVisibility != Truth::no {
            doc /* No Rule 19 maneuver logic is implemented; no use of Rule 12/17 role logic for nonvisual encounters.*/
        }
        out attribute selectionSupported : Boolean = pairwiseScopeSupported and candidateDirectionSupported and escalationAssessmentComplete and role != EncounterRole::unsupported and response != Response::unresolved and immediateDanger == Truth::no and lookoutAdequate == Truth::yes and safeSpeedSupported == Truth::yes and channelObligationsSupported and ((response == Response::monitor or response == Response::holdCourseSpeed) or ownAvoidanceFeasible == Truth::yes) {
            doc /* Support for this pairwise assessment only. CandidateAssessment composes other independently evaluated obligations; this flag alone never approves a trajectory or overall compliance.*/
        }
        out attribute emergencyReviewRequired : Boolean = immediateDanger != Truth::no {
            doc /* Rule 2 assessment remains separate from specific duties; no automatic permission to depart from a rule.*/
        }
        out attribute escalationAssessmentComplete : Boolean = role != EncounterRole::standOn or giveWayAloneSufficient != Truth::unknown {
            doc /* Engineering completeness check: a known permission to act does not establish whether action is already mandatory.*/
        }
        out attribute completeComplianceEstablished : Boolean = false {
            doc /* Rules 2, 5-8 require broader assessment; numeric motion, sound/light signals, Rule 18, Rule 19 and special cases are not fully implemented.*/
        }
        in attribute clearanceEvidenceAdequate : InlandNavigationExperiment::Truth {
            doc /* Independent assessment supporting finally-past-and-clear. May be established despite loss of visual contact; it must not default from a vanished or unreliable track.*/
        }
        in attribute powerEncounter : InlandNavigationExperiment::PowerEncounter;
        in attribute targetSide : InlandNavigationExperiment::TargetSide;
        in attribute headOnDoubt : InlandNavigationExperiment::Truth;
        in attribute passageAgreement : InlandNavigationExperiment::PassageAgreement;
        in attribute specialRiverRulesApply : InlandNavigationExperiment::Truth;
        in attribute ownRiverMotion : InlandNavigationExperiment::RiverMotion;
        in attribute otherRiverMotion : InlandNavigationExperiment::RiverMotion;
        in attribute downboundFollowingCurrent : InlandNavigationExperiment::Truth;
        in attribute ownUnderway : InlandNavigationExperiment::Truth;
        in attribute otherUnderway : InlandNavigationExperiment::Truth;
        in attribute portTurnProposed : InlandNavigationExperiment::Truth;
        in attribute crossAheadProposed : InlandNavigationExperiment::Truth;
        in attribute circumstancesAdmit : InlandNavigationExperiment::Truth;
        out attribute powerPair : Boolean = ownKind == VesselKind::power and otherKind == VesselKind::power;
        out attribute headOnPresumed : Boolean = powerPair and (powerEncounter == PowerEncounter::headOn or headOnDoubt != Truth::no);
        out attribute riverRole : InlandNavigationExperiment::EncounterRole = if not powerPair or specialRiverRulesApply == Truth::no ? EncounterRole::noPairRole else if specialRiverRulesApply == Truth::unknown ? EncounterRole::unsupported else if ownRiverMotion == RiverMotion::crossing and (otherRiverMotion == RiverMotion::upbound or otherRiverMotion == RiverMotion::downbound) ? EncounterRole::giveWay else if otherRiverMotion == RiverMotion::crossing and (ownRiverMotion == RiverMotion::upbound or ownRiverMotion == RiverMotion::downbound) ? EncounterRole::standOn else if ownRiverMotion == RiverMotion::upbound and otherRiverMotion == RiverMotion::downbound and downboundFollowingCurrent == Truth::yes ? EncounterRole::giveWay else if ownRiverMotion == RiverMotion::downbound and otherRiverMotion == RiverMotion::upbound and downboundFollowingCurrent == Truth::yes ? EncounterRole::standOn else if ownRiverMotion == RiverMotion::unresolved or otherRiverMotion == RiverMotion::unresolved or downboundFollowingCurrent == Truth::unknown ? EncounterRole::unsupported else EncounterRole::noPairRole;
        out attribute ownRule18GiveWay : Boolean = ((ownKind == VesselKind::power or ownKind == VesselKind::sailing or ownKind == VesselKind::fishing) and (otherKind == VesselKind::notUnderCommand or otherKind == VesselKind::restrictedManeuverability)) or ((ownKind == VesselKind::power or ownKind == VesselKind::sailing) and otherKind == VesselKind::fishing) or (ownKind == VesselKind::power and otherKind == VesselKind::sailing);
        out attribute otherRule18GiveWay : Boolean = ((otherKind == VesselKind::power or otherKind == VesselKind::sailing or otherKind == VesselKind::fishing) and (ownKind == VesselKind::notUnderCommand or ownKind == VesselKind::restrictedManeuverability)) or ((otherKind == VesselKind::power or otherKind == VesselKind::sailing) and ownKind == VesselKind::fishing) or (otherKind == VesselKind::power and ownKind == VesselKind::sailing);
        out attribute ordinaryRole : InlandNavigationExperiment::EncounterRole = if ownUnderway != Truth::yes or otherUnderway != Truth::yes ? EncounterRole::unsupported else if riverRole != EncounterRole::noPairRole ? riverRole else if ownRule18GiveWay ? EncounterRole::giveWay else if otherRule18GiveWay ? EncounterRole::standOn else if powerPair and headOnPresumed ? EncounterRole::mutualAvoidance else if powerPair and powerEncounter == PowerEncounter::crossing and targetSide == TargetSide::starboardSide ? EncounterRole::giveWay else if powerPair and powerEncounter == PowerEncounter::crossing and targetSide == TargetSide::portSide ? EncounterRole::standOn else sailingRole;
        out attribute headOnStarboardRequired : Boolean = role == EncounterRole::mutualAvoidance and (passageAgreement == PassageAgreement::none or passageAgreement == PassageAgreement::portToPort);
        out attribute agreedStarboardPassage : Boolean = role == EncounterRole::mutualAvoidance and passageAgreement == PassageAgreement::starboardToStarboard;
        out attribute rule17PortTurnRestricted : Boolean = powerPair and powerEncounter == PowerEncounter::crossing and role == EncounterRole::standOn and response == Response::mayAct and targetSide == TargetSide::portSide and circumstancesAdmit != Truth::no;
        out attribute crossAheadRestricted : Boolean = powerPair and powerEncounter == PowerEncounter::crossing and role == EncounterRole::giveWay and circumstancesAdmit != Truth::no;
        out attribute candidateDirectionSupported : Boolean = (not headOnStarboardRequired or (portTurnProposed == Truth::no and starboardTurnProposed == Truth::yes)) and (not rule17PortTurnRestricted or portTurnProposed == Truth::no) and (not crossAheadRestricted or crossAheadProposed == Truth::no) and passageAgreement != PassageAgreement::unresolved;
        in attribute otherNavigatingChannel : InlandNavigationExperiment::Truth;
        in attribute starboardTurnProposed : InlandNavigationExperiment::Truth;
    }
    enum def PowerEncounter {
        enum headOn;
        enum crossing;
        enum none;
        enum uncertain;
    }
    enum def TargetSide {
        enum portSide;
        enum starboardSide;
        enum ahead;
        enum astern;
        enum unresolved;
    }
    enum def RiverMotion {
        enum upbound;
        enum downbound;
        enum crossing;
        enum other;
        enum unresolved;
    }
    enum def PassageAgreement {
        enum none;
        enum portToPort;
        enum starboardToStarboard;
        enum unresolved;
    }
}
package MarineMass {
    private import ScalarValues::*;

    calc def MassProperties {
        in d : Real [29] ordered nonunique;
        in p : Real [41] ordered nonunique;
        in m : Real [10] ordered nonunique;
        in geometry : Real [51] ordered nonunique;
        doc /* Four bodies: hull, wing, keel, rudder. Each geometry block is
         * skin area; skin centroid XYZ; enclosed volume; volume centroid XYZ;
         * minimum thin-wall inertia/thickness; worst bending modulus/thickness;
         * root enclosed area; root perimeter. Last three inputs: ballast centroid XYZ. Geometry units are SI.
         * Foil ribs are unperforated transverse diaphragms. Hull ribs follow
         * a surface-density allocation. Neither earns FDM bending credit. */
        attribute seamKgM2 : Real = 2*m#(1)/m#(2)*m#(3)*(1+p#(1));
        attribute hullSkinKg : Real = geometry#(1)*(m#(4)*m#(5)+d#(21)*(1+p#(1))+m#(6)+seamKgM2);
        attribute hullRibVolume : Real = geometry#(1)*2*m#(5)*m#(7)/d#(25);
        attribute hullRibKg : Real = m#(4)*hullRibVolume;
        attribute hullMass : Real = hullSkinKg+hullRibKg;
        attribute hullMaterialVolume : Real = geometry#(1)*(m#(5)+d#(21)/m#(8)+d#(21)*p#(1)/m#(9))+hullRibVolume;
        attribute wingSkinKg : Real = geometry#(13)*(m#(4)*m#(10)+d#(22)*(1+p#(1))+m#(6)+seamKgM2);
        attribute wingRibVolume : Real = geometry#(17)*m#(5)/d#(26);
        attribute wingRibKg : Real = m#(4)*wingRibVolume;
        attribute wingMass : Real = wingSkinKg+wingRibKg;
        attribute wingMaterialVolume : Real = geometry#(13)*(m#(10)+d#(22)/m#(8)+d#(22)*p#(1)/m#(9))+wingRibVolume;
        attribute keelSkinKg : Real = geometry#(25)*(m#(4)*m#(10)+d#(23)*(1+p#(1))+m#(6)+seamKgM2);
        attribute keelRibVolume : Real = geometry#(29)*m#(5)/d#(26);
        attribute keelRibKg : Real = m#(4)*keelRibVolume;
        attribute keelMass : Real = keelSkinKg+keelRibKg;
        attribute keelMaterialVolume : Real = geometry#(25)*(m#(10)+d#(23)/m#(8)+d#(23)*p#(1)/m#(9))+keelRibVolume;
        attribute rudderSkinKg : Real = geometry#(37)*(m#(4)*m#(10)+d#(24)*(1+p#(1))+m#(6)+seamKgM2);
        attribute rudderRibVolume : Real = geometry#(41)*m#(5)/d#(26);
        attribute rudderRibKg : Real = m#(4)*rudderRibVolume;
        attribute rudderMass : Real = rudderSkinKg+rudderRibKg;
        attribute rudderMaterialVolume : Real = geometry#(37)*(m#(10)+d#(24)/m#(8)+d#(24)*p#(1)/m#(9))+rudderRibVolume;
        attribute batteryMass : Real = d#(17)/p#(13);
        attribute panelMass : Real = 2*d#(18);
        attribute wingDriveMass : Real = p#(22)+p#(21)*d#(19);
        attribute rudderDriveMass : Real = 0.08+p#(21)*d#(20);
        attribute equipmentMass : Real = p#(23)+p#(24)+p#(39);
        attribute totalMass : Real = hullMass+wingMass+keelMass+rudderMass+d#(16)+batteryMass+panelMass+wingDriveMass+rudderDriveMass+equipmentMass;
        attribute moment0 : Real = hullSkinKg*geometry#(2)+hullRibKg*geometry#(2)+wingSkinKg*geometry#(14)+wingRibKg*geometry#(18)+keelSkinKg*geometry#(26)+keelRibKg*geometry#(30)+rudderSkinKg*geometry#(38)+rudderRibKg*geometry#(42)+batteryMass*d#(27)*d#(1)+wingDriveMass*d#(10)*d#(1)+-rudderDriveMass*d#(15)*d#(1)+d#(16)*geometry#(49)+p#(39)*p#(40)*d#(1);
        attribute moment1 : Real = hullSkinKg*geometry#(3)+hullRibKg*geometry#(3)+wingSkinKg*geometry#(15)+wingRibKg*geometry#(19)+keelSkinKg*geometry#(27)+keelRibKg*geometry#(31)+rudderSkinKg*geometry#(39)+rudderRibKg*geometry#(43)+d#(16)*geometry#(50);
        attribute moment2 : Real = hullSkinKg*geometry#(4)+hullRibKg*geometry#(4)+wingSkinKg*geometry#(16)+wingRibKg*geometry#(20)+keelSkinKg*geometry#(28)+keelRibKg*geometry#(32)+rudderSkinKg*geometry#(40)+rudderRibKg*geometry#(44)+d#(16)*geometry#(51)+batteryMass*(-d#(3)+(d#(3)+d#(4))*d#(28))+panelMass*d#(4)+-(wingDriveMass+rudderDriveMass+equipmentMass-p#(39))*d#(3)/2+p#(39)*(d#(4)+p#(41));
        attribute cgX : Real = moment0/totalMass;
        attribute cgY : Real = moment1/totalMass;
        attribute cgZ : Real = moment2/totalMass;
        attribute hullLaminateThickness : Real = d#(21)/m#(8)+d#(21)*p#(1)/m#(9);
        attribute wingLaminateThickness : Real = d#(22)/m#(8)+d#(22)*p#(1)/m#(9);
        attribute keelLaminateThickness : Real = d#(23)/m#(8)+d#(23)*p#(1)/m#(9);
        attribute rudderLaminateThickness : Real = d#(24)/m#(8)+d#(24)*p#(1)/m#(9);
        return result : Real [*] ordered nonunique;
        (totalMass, hullMass, wingMass, keelMass, rudderMass, batteryMass, panelMass, wingDriveMass, rudderDriveMass, equipmentMass,
            cgX,cgY,cgZ,hullMaterialVolume,wingMaterialVolume,keelMaterialVolume,rudderMaterialVolume,
            hullLaminateThickness,wingLaminateThickness,keelLaminateThickness,rudderLaminateThickness)
    }

    calc def InputChecks {
        doc /* Executable preconditions for MassProperties. One denotes a valid
         * input group, zero an invalid one. These preserve the numerical adapter's
         * physical domain; they are not vessel acceptance requirements. */
        in d : Real [29] ordered nonunique;
        in p : Real [41] ordered nonunique;
        attribute positiveDimensions : Real = if d#(1) > 0 and d#(2) > 0 and d#(3) > 0 and d#(4) > 0 and d#(5) > 0 and d#(6) > 0 and d#(8) > 0 and d#(11) > 0 and d#(12) > 0 and d#(13) > 0 and d#(14) > 0 and d#(15) > 0 and d#(17) > 0 and d#(18) > 0 and d#(19) > 0 and d#(20) > 0 and d#(21) > 0 and d#(22) > 0 and d#(23) > 0 and d#(24) > 0 and d#(25) > 0 and d#(26) > 0 ? 1.0 else 0.0;
        attribute nonnegativeBallast : Real = if d#(16) >= 0 ? 1.0 else 0.0;
        attribute positiveBatterySpecificEnergy : Real = if p#(13) > 0 ? 1.0 else 0.0;
        attribute nonnegativeResinRatio : Real = if p#(1) >= 0 ? 1.0 else 0.0;
        return result : Real [4] ordered nonunique;
        (positiveDimensions,nonnegativeBallast,positiveBatterySpecificEnergy,nonnegativeResinRatio)
    }
}

package MarineStructures {
    private import ScalarValues::*;
    calc def DesignMargins {
        in d : Real [29] ordered nonunique;
        in p : Real [41] ordered nonunique;
        in m : Real [21] ordered nonunique;
        in g : Real [60] ordered nonunique;
        in r : Real [12] ordered nonunique;
        in loads : Real [3] ordered nonunique;
        in waterline : Real;
        doc /* g extends the mass geometry vector with deck area at 52 and finite-laminate
         * I/Z pairs for hull, wing, keel and rudder at 53 through 60.
         * Inward polygon offsets define the laminate cross section; no thin-wall
         * stiffness extrapolation is used. Global bending uses worst-direction section modulus.
         * Proof-tip, ballast lateral inertia and operating loads are separate maxima.
         * No FDM bending credit; no buckling, fatigue, impact or joint qualification. */
        attribute modulus : Real = r#(1)*p#(14);
        attribute allowable : Real = r#(2)*p#(14);
        attribute hullI : Real = g#(53);
        attribute wingI : Real = g#(55);
        attribute keelI : Real = g#(57);
        attribute rudderI : Real = g#(59);
        attribute wingSpan : Real = RealFunctions::sqrt(d#(5)*d#(6));
        attribute wingForce : Real = loads#(1)*p#(36);
        attribute keelForce : Real = loads#(2)*p#(36);
        attribute rudderForce : Real = loads#(3)*p#(36);
        attribute hullMoment : Real = m#(1)*p#(35)*d#(1)/4;
        attribute wingMoment : Real = NumericalFunctions::max(wingForce/2,r#(4))*wingSpan;
        attribute keelTipForce : Real = NumericalFunctions::max(r#(4),d#(16)*p#(35)*p#(36));
        attribute keelMoment : Real = NumericalFunctions::max(keelForce/2,keelTipForce)*d#(12);
        attribute rudderMoment : Real = NumericalFunctions::max(rudderForce/2,r#(4))*d#(14);
        attribute hullStressMargin : Real = 1-hullMoment/(g#(54)*allowable);
        attribute wingStressMargin : Real = 1-wingMoment/(g#(56)*allowable);
        attribute keelStressMargin : Real = 1-keelMoment/(g#(58)*allowable);
        attribute rudderStressMargin : Real = 1-rudderMoment/(g#(60)*allowable);
        attribute hullDeflectionMargin : Real = 1-5*2*m#(1)*p#(35)*d#(1)*d#(1)/(384*modulus*hullI*r#(9));
        attribute wingDeflectionMargin : Real = 1-NumericalFunctions::max(wingForce/8,r#(4)/3)*wingSpan*wingSpan/(modulus*wingI*r#(8));
        attribute keelDeflectionMargin : Real = 1-NumericalFunctions::max(keelForce/8,keelTipForce/3)*d#(12)*d#(12)/(modulus*keelI*r#(8));
        attribute rudderDeflectionMargin : Real = 1-NumericalFunctions::max(rudderForce/8,r#(4)/3)*d#(14)*d#(14)/(modulus*rudderI*r#(8));
        attribute panelStressMargin : Real = 1-0.75*r#(3)*d#(25)*d#(25)/(m#(18)*m#(18)*allowable);
        attribute panelDeflectionMargin : Real = 1-5*r#(3)*d#(25)*d#(25)*d#(25)/(32*modulus*m#(18)*m#(18)*m#(18)*r#(10));
        attribute bodyAssembly : Real = m#(2)+m#(5)+m#(7)+m#(8)+m#(9)+m#(10);
        attribute bodyHandlingMargin : Real = 1-bodyAssembly/p#(37);
        attribute wingHandlingMargin : Real = 1-m#(3)/p#(37);
        attribute keelHandlingMargin : Real = 1-(m#(4)+d#(16))/p#(37);
        attribute batteryHandlingMargin : Real = 1-m#(6)/p#(37);
        attribute freeboardMargin : Real = (d#(4)-waterline)/r#(5)-1;
        attribute reserveVolumeMargin : Real = p#(32)*g#(5)/((1+r#(6))*m#(1))-1;
        attribute launchDepthMargin : Real = (r#(7)-(waterline-(2*g#(51)+d#(3)+d#(12))))/r#(7);
        attribute panelAreaMargin : Real = p#(38)*g#(52)/d#(18)-1;
        attribute hullPackingMargin : Real = 1-m#(14)/g#(5);
        attribute wingPackingMargin : Real = 1-m#(15)/g#(17);
        attribute keelPackingMargin : Real = 1-m#(16)/g#(29);
        attribute rudderPackingMargin : Real = 1-m#(17)/g#(41);
        attribute appendages : Real [5] ordered nonunique = MarineAppendages::GeometryMargins(d,r#(11),r#(12));
        attribute keelAspectMargin : Real = appendages#(1);
        attribute rudderAspectMargin : Real = appendages#(2);
        attribute keelRootMargin : Real = appendages#(3);
        attribute rudderStockMargin : Real = appendages#(4);
        attribute sweptSeparationMargin : Real = appendages#(5);
        return result : Real [*] ordered nonunique;
        (hullStressMargin,wingStressMargin,keelStressMargin,rudderStressMargin,hullDeflectionMargin,wingDeflectionMargin,keelDeflectionMargin,rudderDeflectionMargin,panelStressMargin,panelDeflectionMargin,bodyHandlingMargin,wingHandlingMargin,keelHandlingMargin,batteryHandlingMargin,freeboardMargin,reserveVolumeMargin,launchDepthMargin,panelAreaMargin,hullPackingMargin,wingPackingMargin,keelPackingMargin,rudderPackingMargin,keelAspectMargin,rudderAspectMargin,keelRootMargin,rudderStockMargin,sweptSeparationMargin)
    }
}

package TransGorgeCourse {
    private import ScalarValues::*;

    part def MarkerGate {
        attribute markerName : String;
        attribute lightListNumber : Integer;
        attribute longitudeDeg : Real;
        attribute latitudeDeg : Real;
        attribute bearingFromMarkerDeg : Real;
        attribute nearOffsetM : Real;
        attribute farOffsetM : Real;
        attribute sourceCell : String;
        attribute sourceEditionUpdate : String;
    }

    part west : MarkerGate {
        attribute :>> markerName = "Bonneville Pool Lighted Buoy 16";
        attribute :>> lightListNumber = 11835;
        attribute :>> longitudeDeg = -121.8676486;
        attribute :>> latitudeDeg = 45.6918586;
        attribute :>> bearingFromMarkerDeg = 0;
        attribute :>> nearOffsetM = 80;
        attribute :>> farOffsetM = 220;
        attribute :>> sourceCell = "US5WA3DK";
        attribute :>> sourceEditionUpdate = "2.0";
        metadata rationale : ModelingMetadata::Rationale { text = "Western rounding mark near Stevenson: NOAA ENC US5WA3DK and USCG LLNR 11835 identify red Lighted Buoy 16. Round to port through north, west and south offset checkpoints in that order. Use the nominal charted position, never contact or attach to the aid. The 80 m exclusion and 220 m checkpoint extent are project allocations, not statutory stand-offs."; }
    }

    part east : MarkerGate {
        attribute :>> markerName = "Bonneville Pool Lighted Buoy 39";
        attribute :>> lightListNumber = 11985;
        attribute :>> longitudeDeg = -121.461773;
        attribute :>> latitudeDeg = 45.7035806;
        attribute :>> bearingFromMarkerDeg = 180;
        attribute :>> nearOffsetM = 80;
        attribute :>> farOffsetM = 220;
        attribute :>> sourceCell = "US5WA3DP";
        attribute :>> sourceEditionUpdate = "2.0";
        metadata rationale : ModelingMetadata::Rationale { text = "Bingen start/finish reference downstream of Bingen Point boat ramp: green Lighted Buoy 39, NOAA ENC US5WA3DP and USCG LLNR 11985. The virtual gate extends south from the nominal charted buoy position. Launch and retrieval at Bingen Point are outside the scored circuit. Confirm the actual buoy and current notices before launch."; }
    }

    part temporaryWorks {
        attribute longitudeDeg : Real = -121.5225;
        attribute latitudeDeg : Real = 45.7283333333;
        attribute screeningRadiusM : Real = 250;
        metadata rationale : ModelingMetadata::Rationale { text = "2026-10-07 Northwest LNM week 40 page 2 locates railroad bridge work at White Salmon confluence, RM 168.2, through 2026-12-31. The derrick barge stays on station outside work hours. Source: https://www.navcen.uscg.gov/sites/default/files/pdf/lnms/lnm13402026.pdf . Exclude a 250 m analysis buffer around the published point for this snapshot."; }
        metadata issue : ModelingMetadata::Issue { text = "The radius is a conservative scenario allocation, not a surveyed work footprint or statutory stand-off. Replace with confirmed work extent and current notices before release; do not silently expire this exclusion using the computer clock."; }
    }
    part bridgePassage {
        attribute spanIdentifier : String = "0226241BDFAB1596";
        attribute closedClearanceM : Real = 20.4;
        attribute horizontalClearanceM : Real = 74.9;
        attribute pierAllowanceM : Real = 10;
        attribute verticalAllowanceM : Real = 2;
        attribute referenceApproachM : Real = 150;
        attribute source : String = "https://www.portofhoodriver.com/bridge-lift-request";
        metadata rationale : ModelingMetadata::Rationale { text = "Select the charted Hood River lifting span, closed, for both legs. ENC US5WA3DP LNAM 0226241BDFAB1596 supplies the polygon and conservative 20.4 m closed clearance; the Port reports 20.42 m at its stated average river height. Adjacent spans without clearance evidence are excluded. No bridge opening is part of the mission. Vertical acceptance subtracts measured pool rise, vessel air draft including motion, and a 2 m project uncertainty allowance from chart clearance. PDR must verify the local stage datum; launch must check current works and pool stage. The 10 m pier allowance is a planning allocation, not a legal stand-off."; }
    }
    part policy {
        attribute coordinateDatum : String = "WGS84 longitude/latitude degrees; bearings clockwise from true north; offsets in meters";
        attribute chartEvidence : String = "evidence/course/2026-10-11/chart-features.geojson";
        attribute sourceCatalog : String = "https://www.charts.noaa.gov/ENCs/ENCProdCat_19115.xml";
        attribute sourceLightList : String = "https://www.navcen.uscg.gov/sites/default/files/pdf/lightLists/weeklyUpdates/v6WeeklyChanges.pdf";
        attribute chartCatalogDate : String = "2026-10-10";
        attribute lightListDate : String = "2026-10-07";
        attribute gatesAcceptedForLaunch : Boolean = false;
        attribute damTransitPermitted : Boolean = false;
        attribute lockApproachTransitPermitted : Boolean = false;
        attribute hasCompletionDeadline : Boolean = false;
        attribute minimumChartDepthM : Real = 2;
        attribute shoreClearanceM : Real = 30;
        attribute restrictionClearanceM : Real = 50;
        attribute obstacleClearanceM : Real = 30;
        attribute routingGridM : Real = 40;
        attribute referenceLegLengthM : Real = 32994.546297358545;
        metadata referenceLengthBasis : ModelingMetadata::Rationale { text = "Half the complete chart-domain reference circuit including the buoy rounding generated from this gate and clearance configuration by tools.boat_analysis.environment.routing. This equivalent leg length preserves full circuit distance in the symmetric sizing calculation; the mission simulation uses the distinct legs. This is a nominal sizing-analysis distance, not a prescribed sailing track; tacks and avoidance increase traveled distance. Regeneration checks this value against the chart-derived route."; }
        metadata routingRationale : ModelingMetadata::Rationale { text = "Initial routing allocations for the small-vessel analysis: chart depth at least 2 m, 30 m from charted land/obstructions and 50 m from excluded charted areas. These are project planning margins, not legal stand-off distances. Actual draft, pool stage, maneuvering, uncertainty and bridge clearances require separate assessment. Grid resolution is a numerical setting, not a vessel requirement."; }
        attribute gateNames : String [5] ordered nonunique = ("eastGate", "westGate", "turnGate", "returnGate", "eastGate");
        attribute gateDirections : Integer [5] ordered nonunique = (-1,1,1,1,1);
        attribute crossingSequence : String = "Cross Bingen gate downstream; pass north, west and south of buoy 16 in order, keeping the buoy to port; cross Bingen gate upstream to finish. Maintain the modeled marker exclusion throughout. Launch and retrieval are outside the scored course.";
        metadata rationale : ModelingMetadata::Rationale { text = "The route stays in Bonneville Pool. Gate segments are defined relative to existing aids, with 80 m minimum nominal marker offset. Chart-derived polygons, water depth and local notices constrain route planning; neither the marker-to-marker chord nor the commercial fairway is the whole permitted sailing corridor. Completion has no elapsed-time deadline. A computational horizon reports censoring rather than failure."; }
        metadata issue : ModelingMetadata::Issue { text = "Gate proposal for mission analysis, not a launch release. Verify complete segment clearance and maneuvering/drift margins, current MSI notices, current pool stage, bridge passage and autonomous traffic avoidance. A route through charted water does not establish safe operation. No universal vessel stand-off distance is inferred from navigation rules."; }
    }
    dependency courseBasis from policy to GorgeChallenge::courseCompletion;

    analysis GateGeometry {
        out attribute bridgeSpanIdentifier : String = bridgePassage.spanIdentifier;
        out attribute bridgePierAllowanceM : Real = bridgePassage.pierAllowanceM;
        out attribute bridgeApproachM : Real = bridgePassage.referenceApproachM;
        out attribute referenceLegLengthM : Real = policy.referenceLegLengthM;
        out attribute temporaryWorks : Real [3] ordered nonunique = (TransGorgeCourse::temporaryWorks.longitudeDeg, TransGorgeCourse::temporaryWorks.latitudeDeg, TransGorgeCourse::temporaryWorks.screeningRadiusM);
        out attribute westGate : Real [5] ordered nonunique = (west.longitudeDeg, west.latitudeDeg, west.bearingFromMarkerDeg, west.nearOffsetM, west.farOffsetM);
        out attribute turnGate : Real [5] ordered nonunique = (west.longitudeDeg, west.latitudeDeg, 270, west.nearOffsetM, west.farOffsetM);
        out attribute returnGate : Real [5] ordered nonunique = (west.longitudeDeg, west.latitudeDeg, 180, west.nearOffsetM, west.farOffsetM);
        out attribute eastGate : Real [5] ordered nonunique = (east.longitudeDeg, east.latitudeDeg, east.bearingFromMarkerDeg, east.nearOffsetM, east.farOffsetM);
        out attribute routing : Real [5] ordered nonunique = (policy.minimumChartDepthM, policy.shoreClearanceM, policy.restrictionClearanceM, policy.obstacleClearanceM, policy.routingGridM);
    }
}

package BlueDogMissionScope {
    private import ScalarValues::*;
    enum def MissionKind { gorge; futureOcean; futureEndurance; }
    metadata def Applicability {
        attribute mission : MissionKind;
    }
    metadata applicability : Applicability about GorgeChallenge::RepeatedOperation {
        mission = MissionKind::futureEndurance;
    }
    part current {
        attribute designObjective : String = "Maximize probability of completing one unassisted sail-only Gorge round trip within a selected weather window";
        attribute requiresOceanQualification : Boolean = false;
        attribute requiresIndefiniteOperation : Boolean = false;
        attribute requiresRepeatableEnergyBalance : Boolean = false;
        attribute hasCompletionDeadline : Boolean = false;
        metadata rationale : ModelingMetadata::Rationale { text = "Owner decision: focus on the finite Gorge challenge. Retain finite battery accounting and reserve protection; no fixed-duration campaign constrains acceptance; no Hawaii route, saltwater profile or indefinite operation constraint is inherited. Passage time, speed-dependent failure exposure and weather-window completion should be compared together. Safety dispositions remain independent launch gates."; }
        metadata issue : ModelingMetadata::Issue { text = "Archived studies retain their original daily-balance screens. Active Gorge sizing uses instantaneous peak-power checks; chronological mission execution must establish finite energy feasibility. Speed/load-dependent failure evidence and a valid planing model remain necessary for comparing hull regimes."; }
    }
    part future {
        attribute designObjective : String = "Define a separate Hawaii mission and persistent-operation capability";
        attribute acceptanceAllocated : Boolean = false;
        metadata rationale : ModelingMetadata::Rationale { text = "Hawaii remains a future mission with independently allocated route, weather, endurance, communications, maintenance and recovery constraints. Existing ocean limits and repeating-energy cases are candidate future studies; they do not constrain Gorge acceptance."; }
    }
    dependency currentMission from current to GorgeChallenge::transGorgeChallenge;
    dependency futureMission from future to BlueDog::Goals::hawaiiVoyage;
}

package GorgeChallenge {
    doc /* Independent trans-gorge autonomous sailing challenge.
     * Inspired by the structure of the Microtransat rules:
     * https://microtransat.org/content.php?p=rules&top=rules
     * This is a separate project challenge, not a Microtransat entry or endorsement.
     * Vessel architecture and communications technology are unrestricted; overall length is limited to 1.2 m.
     * The Gorge is the proving ground for a longer-term voyage toward Hawaii.
     * Marker-referenced virtual gates are defined in TransGorgeCourse.
     * There is no completion deadline. The vehicle defines candidate environmental qualification profiles; no dam passage is permitted.
     */
    private import RequirementDerivation::*;
    private import ISQ::*;
    private import SI::*;
    attribute maximumOverallLength : LengthValue = 1.2 [m];
    requirement def <'C-000'> TransGorgeChallenge {
        metadata workStatus : ModelingMetadata::StatusInfo { status = ModelingMetadata::StatusKind::open; }
        doc /* The vessel shall complete the Trans-Gorge challenge under C-001, C-003 through C-010 and C-012 through C-027.*/
        metadata rationale : ModelingMetadata::Rationale { text = "One Bingen–Stevenson–Bingen circuit defines the finite challenge. Repeated circuits are a separate future endurance objective."; }
    }
    requirement transGorgeChallenge : TransGorgeChallenge;
    requirement def <'C-001'> CourseCompletion {
        metadata workStatus : ModelingMetadata::StatusInfo { status = ModelingMetadata::StatusKind::open; }
        doc /* The vessel shall cross the configured Bingen departure, buoy 16 rounding checkpoints and Bingen finish gates in order during one attempt. */
        comment conditions /* TransGorgeCourse defines nominal marker references and directed finite gate segments. Completion has no elapsed-time deadline. Position history must demonstrate crossings; touching a gate line alone does not count. */
        metadata issue : ModelingMetadata::Issue { text = "The marker-based gate proposal remains subject to the course safety review before launch; route corridor and current notice exclusions must accompany the accepted configuration."; }
    }
    requirement def <'C-002'> RepeatedOperation {
        metadata workStatus : ModelingMetadata::StatusInfo { status = ModelingMetadata::StatusKind::open; }
        doc /* After its first circuit, the vessel should repeat Bingen–Stevenson–Bingen autonomously for as long as practical. */
        comment notes /* Future endurance objective, excluded from finite challenge acceptance. */
        metadata issue : ModelingMetadata::Issue { text = "No fixed objective endurance duration has been selected."; }
    }
    requirement def <'C-003'> UnassistedAttempt {
        metadata workStatus : ModelingMetadata::StatusInfo { status = ModelingMetadata::StatusKind::open; }
        doc /* A qualifying attempt shall complete the round trip without operator intervention. */
        comment conditions /* Passive live monitoring and autonomous polling of weather services are permitted. Any operator-supplied update, remote emergency abort or manual control ends qualification. Weather data must be obtained by the system without manual operator submission. */
        comment restartConditions /* After intervention, a new qualifying attempt begins only with a new downstream crossing of the departure gate. Previous partial progress does not transfer. */
    }
    requirement def <'C-004'> SailingPropulsion {
        metadata workStatus : ModelingMetadata::StatusInfo { status = ModelingMetadata::StatusKind::open; }
        doc /* A qualifying attempt shall use sailing propulsion without auxiliary motor propulsion. */
        comment conditions /* An auxiliary motor may remain installed. Motor use is permitted during separate development tests and vessel recovery; use during an attempt ends its qualification. */
        comment notes /* The restriction concerns propulsion, not onboard electrical power. */
    }
    requirement def <'C-005'> LiveObservation {
        metadata workStatus : ModelingMetadata::StatusInfo { status = ModelingMetadata::StatusKind::open; }
        doc /* The vessel shall deliver position, operating mode and health updates at intervals no greater than 30 seconds while the monitoring link is available. */
        comment conditions /* C-020 governs autonomous continuation, retention and telemetry replay during monitoring-link outages. */
        metadata issue : ModelingMetadata::Issue { text = "LTE-M-class throughput is a provisional vehicle design assumption, not a mandated challenge technology. End-to-end delivery qualification and stale-data presentation are allocated to the vehicle."; }
    }
    requirement def <'C-006'> EmergencyIntervention {
        metadata workStatus : ModelingMetadata::StatusInfo { status = ModelingMetadata::StatusKind::open; }
        doc /* The vessel shall permit remote emergency abort or manual control when a command link is available. */
        comment conditions /* Use disqualifies the attempt as unassisted. */
        metadata issue : ModelingMetadata::Issue { text = "Owner-approved policy: autonomous safety abort does not wait for operator contact. Recovery may use motor propulsion; operator-directed relocation or motor-sailing after abort never restores qualification."; }
    }
    requirement courseCompletion : CourseCompletion;
    requirement repeatedOperation : RepeatedOperation;
    requirement unassistedAttempt : UnassistedAttempt;
    requirement sailingPropulsion : SailingPropulsion;
    requirement liveObservation : LiveObservation;
    requirement emergencyIntervention : EmergencyIntervention;
    requirement def <'C-007'> NavigationRules {
        metadata workStatus : ModelingMetadata::StatusInfo { status = ModelingMetadata::StatusKind::open; }
        doc /* The vessel shall comply with the U.S. Inland Navigation Rules (33 CFR parts 83 through 90) and applicable local navigation provisions throughout the attempt on the approved Gorge course.*/
        comment conditions /* Evaluate the actual encounter and visibility conditions, including lookout, collision-risk assessment, avoidance action, safe speed, overtaking, sailing encounters and narrow-channel obligations. A safety action takes precedence over preserving attempt qualification. */
        metadata rationale : ModelingMetadata::Rationale { text = "USCG Navigation Rules: https://www.navcen.uscg.gov/navigation-rules-amalgamated . Detailed encounter cases and quantitative acceptance allocations belong to the vehicle analysis, not the independent challenge. Small size and sail propulsion do not exempt the vessel from collision avoidance or channel non-impediment."; }
        comment processResponsibilities /* C-028 identifies entrant applicability review; C-029 controls the organizer rule and notice baseline; C-030 governs entry evidence; C-031 identifies operator safety intervention; C-032 governs adjudication. These preserve the C-007 entry and qualification policy. */
        comment complianceSources /* Governing source: https://www.ecfr.gov/current/title-33/chapter-I/subchapter-E . Applicability: https://www.ecfr.gov/current/title-33/chapter-I/subchapter-E/part-83/subpart-A/section-83.01 . Source-linked verification cases in GorgeChallengeVerification cover applicability, lookout/avoidance, encounter conduct, channel/visibility and signals. Their verdicts remain inconclusive pending accepted evidence; traceability is not a compliance finding.*/
    }
    requirement def <'C-008'> RestrictedWaters {
        metadata workStatus : ModelingMetadata::StatusInfo { status = ModelingMetadata::StatusKind::open; }
        doc /* The vessel shall remain outside waters prohibited to the attempt configuration. */
        comment conditions /* Include dam restricted areas, lock approaches excluded by the challenge, and applicable temporary safety/security zones or closures. Use the chart and notice set applicable to the attempt. */
        metadata rationale : ModelingMetadata::Rationale { text = "33 CFR 207.718 defines site-specific dam restrictions and lock-approach authority: https://www.ecfr.gov/current/title-33/chapter-II/part-207/section-207.718 . The course stays between the dams and requires no lock passage. Do not replace mapped restrictions with an invented universal stand-off radius."; }
    }
    requirement def <'C-009'> TrafficCoexistence {
        metadata workStatus : ModelingMetadata::StatusInfo { status = ModelingMetadata::StatusKind::open; }
        doc /* The vessel shall complete the course without collision with other waterway users. */
        comment conditions /* The operating context includes commercial tows, passenger vessels, fishing craft, recreational powerboats, sailing vessels and people in the water. Channel non-impediment and encounter conduct remain independently required by C-007. The vehicle analysis defines representative and adverse traffic scenarios and assesses maneuver feasibility. */
        metadata rationale : ModelingMetadata::Rationale { text = "The course is shared water, not a closed test range. Typical traffic and uncertainty in other users' behavior are part of mission validation; AIS absence is not evidence of clear water. Numeric separation allocations must be justified by encounter geometry and vessel performance."; }
    }
    requirement navigationRules : NavigationRules;
    requirement restrictedWaters : RestrictedWaters;
    requirement trafficCoexistence : TrafficCoexistence;
    #derivation connection challengeNavigationRules {
        metadata workStatus : ModelingMetadata::StatusInfo { status = ModelingMetadata::StatusKind::open; }
        metadata rationale : ModelingMetadata::Rationale { text = "C-000 includes this obligation independently of course progress or elapsed time."; }
        end #original source ::> transGorgeChallenge;
        end #derive target ::> navigationRules;
    }
    #derivation connection challengeRestrictedWaters {
        metadata workStatus : ModelingMetadata::StatusInfo { status = ModelingMetadata::StatusKind::open; }
        metadata rationale : ModelingMetadata::Rationale { text = "C-000 includes this obligation independently of course progress or elapsed time."; }
        end #original source ::> transGorgeChallenge;
        end #derive target ::> restrictedWaters;
    }
    #derivation connection challengeTrafficCoexistence {
        metadata workStatus : ModelingMetadata::StatusInfo { status = ModelingMetadata::StatusKind::open; }
        metadata rationale : ModelingMetadata::Rationale { text = "C-000 includes this obligation independently of course progress or elapsed time."; }
        end #original source ::> transGorgeChallenge;
        end #derive target ::> trafficCoexistence;
    }
    #derivation connection challengeRuleCourseCompletion {
        metadata workStatus : ModelingMetadata::StatusInfo { status = ModelingMetadata::StatusKind::open; }
        metadata rationale : ModelingMetadata::Rationale { text = "This rule is explicitly included in C-000; C-002 retains its objective-only status."; }
        end #original source ::> transGorgeChallenge;
        end #derive target ::> courseCompletion;
    }
    dependency futureEnduranceBasis from repeatedOperation to courseCompletion {
        metadata rationale : ModelingMetadata::Rationale { text = "Future repeated operation uses the same ordered course geometry. This design dependency does not impose repeating endurance on the current finite qualification mission."; }
    }
    #derivation connection challengeRuleUnassistedAttempt {
        metadata workStatus : ModelingMetadata::StatusInfo { status = ModelingMetadata::StatusKind::open; }
        metadata rationale : ModelingMetadata::Rationale { text = "This rule is explicitly included in C-000; C-002 retains its objective-only status."; }
        end #original source ::> transGorgeChallenge;
        end #derive target ::> unassistedAttempt;
    }
    #derivation connection challengeRuleSailingPropulsion {
        metadata workStatus : ModelingMetadata::StatusInfo { status = ModelingMetadata::StatusKind::open; }
        metadata rationale : ModelingMetadata::Rationale { text = "This rule is explicitly included in C-000; C-002 retains its objective-only status."; }
        end #original source ::> transGorgeChallenge;
        end #derive target ::> sailingPropulsion;
    }
    #derivation connection challengeRuleLiveObservation {
        metadata workStatus : ModelingMetadata::StatusInfo { status = ModelingMetadata::StatusKind::open; }
        metadata rationale : ModelingMetadata::Rationale { text = "This rule is explicitly included in C-000; C-002 retains its objective-only status."; }
        end #original source ::> transGorgeChallenge;
        end #derive target ::> liveObservation;
    }
    #derivation connection challengeRuleEmergencyIntervention {
        metadata workStatus : ModelingMetadata::StatusInfo { status = ModelingMetadata::StatusKind::open; }
        metadata rationale : ModelingMetadata::Rationale { text = "This rule is explicitly included in C-000; C-002 retains its objective-only status."; }
        end #original source ::> transGorgeChallenge;
        end #derive target ::> emergencyIntervention;
    }
    requirement def <'C-010'> OverallLength {
        metadata workStatus : ModelingMetadata::StatusInfo { status = ModelingMetadata::StatusKind::open; }
        doc /* The vessel overall length shall not exceed 1.2 m. */
        attribute measuredOverallLength : LengthValue;
        require constraint lengthLimit { measuredOverallLength > 0 [m] and measuredOverallLength <= maximumOverallLength }
        comment conditions /* Measure maximum fore-and-aft extent, including rudders, rig projections, antennas and other equipment, across normal operating configurations. Hull arrangement is unrestricted. */
        metadata rationale : ModelingMetadata::Rationale { text = "Half the Microtransat 2.4 m overall-length entry limit; owner-selected challenge constraint."; }
    }
    requirement overallLength : OverallLength;
    #derivation connection deriveOverallLength {
        metadata workStatus : ModelingMetadata::StatusInfo { status = ModelingMetadata::StatusKind::open; }
        end #original source ::> transGorgeChallenge;
        end #derive target ::> overallLength;
    }
    requirement def <'C-012'> SafetyCapabilityAbort {
        metadata workStatus : ModelingMetadata::StatusInfo { status = ModelingMetadata::StatusKind::open; }
        doc /* The vessel shall autonomously terminate qualification when a required safety capability is lost. */
        comment conditions /* A demonstrated backup preserving the function permits continuation. Darkness alone is not a fault. Fog triggers this rule when it compromises required capability. */
        metadata rationale : ModelingMetadata::Rationale { text = "Abort is based on capability, not individual component failure."; }
    }
    requirement safetyCapabilityAbort : SafetyCapabilityAbort;
    #derivation connection deriveSafetyCapabilityAbort {
        metadata workStatus : ModelingMetadata::StatusInfo { status = ModelingMetadata::StatusKind::open; }
        end #original source ::> transGorgeChallenge;
        end #derive target ::> safetyCapabilityAbort;
    }
    requirement def <'C-013'> AutonomousShoreRecovery {
        metadata workStatus : ModelingMetadata::StatusInfo { status = ModelingMetadata::StatusKind::open; }
        doc /* Following a safety abort, the vessel shall autonomously initiate recovery toward a suitable shore-accessible retrieval location. */
        comment conditions /* Do not wait for operator intervention or communications. Select a viable route based on remaining capabilities. Intentional grounding at a suitable accessible shore is permitted. */
        metadata rationale : ModelingMetadata::Rationale { text = "Owner-selected recovery policy; residual risk of movement after traffic-sensing failure requires explicit analysis and review, not assumed acceptance."; }
    }
    requirement autonomousShoreRecovery : AutonomousShoreRecovery;
    #derivation connection deriveAutonomousShoreRecovery {
        metadata workStatus : ModelingMetadata::StatusInfo { status = ModelingMetadata::StatusKind::open; }
        end #original source ::> transGorgeChallenge;
        end #derive target ::> autonomousShoreRecovery;
    }
    requirement def <'C-014'> AbortAlert {
        metadata workStatus : ModelingMetadata::StatusInfo { status = ModelingMetadata::StatusKind::open; }
        doc /* The vessel shall attempt immediate transmission of an abort alert when an abort is declared. */
        comment conditions /* Queue the alert while communications are unavailable and transmit when contact returns. */
        metadata rationale : ModelingMetadata::Rationale { text = "Operator awareness supports shore retrieval without being a prerequisite for recovery."; }
    }
    requirement abortAlert : AbortAlert;
    #derivation connection deriveAbortAlert {
        metadata workStatus : ModelingMetadata::StatusInfo { status = ModelingMetadata::StatusKind::open; }
        end #original source ::> transGorgeChallenge;
        end #derive target ::> abortAlert;
    }
    requirement def <'C-015'> NoLittering {
        metadata workStatus : ModelingMetadata::StatusInfo { status = ModelingMetadata::StatusKind::open; }
        doc /* The vessel shall support recovery without abandonment of the vessel or its major components in the waterway. */
        comment conditions /* Apply flotation, retention and post-capsize recovery obligations C-016 through C-018. */
        metadata rationale : ModelingMetadata::Rationale { text = "Owner intent: no littering. This is a recoverability obligation, not a guarantee against every conceivable casualty."; }
    }
    requirement noLittering : NoLittering;
    #derivation connection deriveNoLittering {
        metadata workStatus : ModelingMetadata::StatusInfo { status = ModelingMetadata::StatusKind::open; }
        end #original source ::> transGorgeChallenge;
        end #derive target ::> noLittering;
    }
    requirement def <'C-016'> CasualtyFlotation {
        metadata workStatus : ModelingMetadata::StatusInfo { status = ModelingMetadata::StatusKind::open; }
        doc /* The vessel shall remain afloat following capsize or hull flooding. */
        comment conditions /* Demonstrate in the declared casualty qualification conditions for the interval needed to execute shore recovery. */
        metadata rationale : ModelingMetadata::Rationale { text = "Derived from recoverability; casualty definition and exposure allocations require SRR review."; }
    }
    requirement casualtyFlotation : CasualtyFlotation;
    #derivation connection deriveCasualtyFlotation {
        metadata workStatus : ModelingMetadata::StatusInfo { status = ModelingMetadata::StatusKind::open; }
        end #original source ::> noLittering;
        end #derive target ::> casualtyFlotation;
    }
    requirement def <'C-017'> MajorComponentRetention {
        metadata workStatus : ModelingMetadata::StatusInfo { status = ModelingMetadata::StatusKind::open; }
        doc /* The vessel shall retain its rig, ballast and battery following capsize or hull flooding. */
        comment conditions /* Use the same casualty qualification conditions as C-016. */
        metadata rationale : ModelingMetadata::Rationale { text = "Retained major components prevent debris and support retrieval."; }
    }
    requirement majorComponentRetention : MajorComponentRetention;
    #derivation connection deriveMajorComponentRetention {
        metadata workStatus : ModelingMetadata::StatusInfo { status = ModelingMetadata::StatusKind::open; }
        end #original source ::> noLittering;
        end #derive target ::> majorComponentRetention;
    }
    requirement def <'C-018'> CapsizeRecovery {
        metadata workStatus : ModelingMetadata::StatusInfo { status = ModelingMetadata::StatusKind::open; }
        doc /* The vessel shall demonstrate autonomous travel to a suitable shore retrieval location following capsize without communications. */
        comment conditions /* Self-righting is not prescribed; inverted recovery is permitted. Auxiliary propulsion ends qualification. Demonstrate against declared course recovery conditions. */
        metadata rationale : ModelingMetadata::Rationale { text = "Limp recovery is the required outcome; hull architecture remains open."; }
    }
    requirement capsizeRecovery : CapsizeRecovery;
    #derivation connection deriveCapsizeRecovery {
        metadata workStatus : ModelingMetadata::StatusInfo { status = ModelingMetadata::StatusKind::open; }
        end #original source ::> noLittering;
        end #derive target ::> capsizeRecovery;
    }
    requirement def <'C-019'> UnattachedPassage {
        metadata workStatus : ModelingMetadata::StatusInfo { status = ModelingMetadata::StatusKind::open; }
        doc /* A qualifying attempt shall remain afloat and unattached throughout the scored passage. */
        comment conditions /* Grounding, anchoring, attaching to shore or entering designated refuge ends qualification. Safe waiting under sail is permitted and counts toward elapsed exposure. */
        metadata rationale : ModelingMetadata::Rationale { text = "Refuge does not preserve partial qualifying progress."; }
    }
    requirement unattachedPassage : UnattachedPassage;
    #derivation connection deriveUnattachedPassage {
        metadata workStatus : ModelingMetadata::StatusInfo { status = ModelingMetadata::StatusKind::open; }
        end #original source ::> transGorgeChallenge;
        end #derive target ::> unattachedPassage;
    }
    requirement def <'C-020'> OutageAutonomy {
        metadata workStatus : ModelingMetadata::StatusInfo { status = ModelingMetadata::StatusKind::open; }
        doc /* Loss of communications alone shall not terminate an otherwise safe qualifying attempt. */
        comment conditions /* Continue navigation and retain telemetry onboard; replay retained data after reconnection. */
        metadata rationale : ModelingMetadata::Rationale { text = "Onboard safety and recovery do not depend on contact."; }
    }
    requirement communicationOutageAutonomy : OutageAutonomy;
    #derivation connection deriveOutageAutonomy {
        metadata workStatus : ModelingMetadata::StatusInfo { status = ModelingMetadata::StatusKind::open; }
        end #original source ::> transGorgeChallenge;
        end #derive target ::> communicationOutageAutonomy;
    }
    requirement def <'C-021'> ForecastAdmission {
        metadata workStatus : ModelingMetadata::StatusInfo { status = ModelingMetadata::StatusKind::open; }
        doc /* Launch authorization shall require a forecast window assessed to support the complete round trip with waiting and recovery margins. */
        comment conditions /* Use the declared mission configuration and forecast-conditioned scenarios. No fixed completion deadline applies. */
        metadata rationale : ModelingMetadata::Rationale { text = "Whole-mission assessment replaces an arbitrary sailing-speed floor."; }
    }
    requirement forecastAdmission : ForecastAdmission;
    #derivation connection deriveForecastAdmission {
        metadata workStatus : ModelingMetadata::StatusInfo { status = ModelingMetadata::StatusKind::open; }
        end #original source ::> transGorgeChallenge;
        end #derive target ::> forecastAdmission;
    }
    requirement def <'C-022'> WeatherOutageContinuation {
        metadata workStatus : ModelingMetadata::StatusInfo { status = ModelingMetadata::StatusKind::open; }
        doc /* The vessel shall permit continued qualification during weather-service outage only while the last forecast remains applicable and required safety capabilities remain available. */
        comment conditions /* Forecast applicability must cover remaining passage and recovery options; assess against observations. */
        metadata rationale : ModelingMetadata::Rationale { text = "Loss of data access alone is not an abort trigger."; }
    }
    requirement weatherOutageContinuation : WeatherOutageContinuation;
    #derivation connection deriveWeatherOutageContinuation {
        metadata workStatus : ModelingMetadata::StatusInfo { status = ModelingMetadata::StatusKind::open; }
        end #original source ::> transGorgeChallenge;
        end #derive target ::> weatherOutageContinuation;
    }
    requirement def <'C-023'> CourseRecoveryReserve {
        metadata workStatus : ModelingMetadata::StatusInfo { status = ModelingMetadata::StatusKind::open; }
        doc /* The vessel shall protect sufficient energy to reach a suitable shore retrieval location from its current course position. */
        comment conditions /* Account for adverse current, essential onboard loads and uncertainty along the recovery route. No fixed motor-runtime reserve is substituted for route analysis. */
        metadata rationale : ModelingMetadata::Rationale { text = "Reserve follows the course and available recovery destinations."; }
    }
    requirement courseRecoveryReserve : CourseRecoveryReserve;
    #derivation connection deriveCourseRecoveryReserve {
        metadata workStatus : ModelingMetadata::StatusInfo { status = ModelingMetadata::StatusKind::open; }
        end #original source ::> transGorgeChallenge;
        end #derive target ::> courseRecoveryReserve;
    }
    requirement def <'C-024'> ReserveAbort {
        metadata workStatus : ModelingMetadata::StatusInfo { status = ModelingMetadata::StatusKind::open; }
        doc /* The vessel shall initiate autonomous recovery before further mission continuation would compromise the course-dependent recovery reserve. */
        comment conditions /* Include the decision and maneuver margin needed to enter recovery. */
        metadata rationale : ModelingMetadata::Rationale { text = "Protecting reserve requires timely action, not only energy monitoring."; }
    }
    requirement reserveAbort : ReserveAbort;
    #derivation connection deriveReserveAbort {
        metadata workStatus : ModelingMetadata::StatusInfo { status = ModelingMetadata::StatusKind::open; }
        end #original source ::> transGorgeChallenge;
        end #derive target ::> reserveAbort;
    }
    requirement def <'C-025'> NightOperation {
        metadata workStatus : ModelingMetadata::StatusInfo { status = ModelingMetadata::StatusKind::open; }
        doc /* The vessel shall support qualifying operation in darkness. */
        comment conditions /* Required navigation, traffic safety and observation functions remain applicable. Nightfall alone does not require refuge. */
        metadata rationale : ModelingMetadata::Rationale { text = "Passage duration is uncertain and may include overnight sailing."; }
    }
    requirement nightOperation : NightOperation;
    #derivation connection deriveNightOperation {
        metadata workStatus : ModelingMetadata::StatusInfo { status = ModelingMetadata::StatusKind::open; }
        end #original source ::> transGorgeChallenge;
        end #derive target ::> nightOperation;
    }
    requirement def <'C-026'> AbortPersistence {
        metadata workStatus : ModelingMetadata::StatusInfo { status = ModelingMetadata::StatusKind::open; }
        doc /* An aborted attempt shall remain disqualified until a new attempt begins at the departure gate. */
        comment conditions /* No autonomous resumption from refuge. Operator-commanded relocation is permitted outside qualification. */
        metadata rationale : ModelingMetadata::Rationale { text = "Recovery cannot silently resume a partial challenge."; }
    }
    requirement abortPersistence : AbortPersistence;
    #derivation connection deriveAbortPersistence {
        metadata workStatus : ModelingMetadata::StatusInfo { status = ModelingMetadata::StatusKind::open; }
        end #original source ::> transGorgeChallenge;
        end #derive target ::> abortPersistence;
    }
    requirement def <'C-027'> RecoveryConspicuity {
        metadata workStatus : ModelingMetadata::StatusInfo { status = ModelingMetadata::StatusKind::open; }
        doc /* The vessel shall present conspicuous recovery indications during autonomous shore recovery. */
        comment conditions /* Allocate indications consistently with applicable navigation signals; no light or sound configuration is prescribed here. */
        metadata rationale : ModelingMetadata::Rationale { text = "Prompt recovery and operator alerts do not replace visibility to other users."; }
    }
    requirement recoveryConspicuity : RecoveryConspicuity;
    #derivation connection deriveRecoveryConspicuity {
        metadata workStatus : ModelingMetadata::StatusInfo { status = ModelingMetadata::StatusKind::open; }
        end #original source ::> transGorgeChallenge;
        end #derive target ::> recoveryConspicuity;
    }
    comment trafficCourtesyGuidance /* Entrants are encouraged to choose routes and operating windows that reduce encounters with other waterway users. This is nonbinding guidance, not an entry or adjudication criterion. Another vessel changing course or speed is not by itself a breach. Navigation-rule compliance, applicable nonimpediment duties and collision avoidance remain governed by C-007 and C-009.*/
    requirement def <'C-028'> NavigationRuleApplicability {
        doc /* Before entry approval, the entrant shall submit a configuration-specific navigation-rule applicability assessment. */
        comment conditions /* Before entry approval, the entrant shall submit a rule-applicability assessment for the identified vessel, propulsion modes, course and operating conditions. Identify the governing provisions and current local restrictions, required lights/shapes/sound signals, applicable exceptions and supporting authority. */
        metadata workStatus : ModelingMetadata::StatusInfo { status = ModelingMetadata::StatusKind::open; }
    }
    requirement navigationRuleApplicability : NavigationRuleApplicability;
    dependency navigationRuleApplicabilityBasis from navigationRuleApplicability to navigationRules;
    requirement def <'C-029'> NavigationRuleBaseline {
        doc /* The organizer shall record and maintain the reviewed rule and notice baseline for the attempt. */
        comment conditions /* The organizer shall record the reviewed rule and notice baseline; later effective changes shall be reviewed before launch. */
        metadata workStatus : ModelingMetadata::StatusInfo { status = ModelingMetadata::StatusKind::open; }
    }
    requirement navigationRuleBaseline : NavigationRuleBaseline;
    dependency navigationRuleBaselineBasis from navigationRuleBaseline to navigationRules;
    requirement def <'C-030'> NavigationEntryEvidence {
        doc /* The organizer shall approve entry only when the configuration-specific navigation evidence satisfies the entry-evidence conditions. */
        comment conditions /* Entry approval shall require organizer acceptance of configuration-specific evidence covering relevant sailing, overtaking, crossing and constrained-water encounters, uncertain classification, restricted visibility, degraded sensing and safety intervention. Record assumptions, observation and maneuver limits, pass/fail criteria, physical demonstrations, simulation coverage and remaining exclusions. Unsupported conditions shall be excluded from admission; unresolved capability within admitted conditions prevents entry approval. Entrants shall justify detection distances, margins and maneuver capability. Passing a limited software rule subset does not establish compliance with C-007. */
        metadata workStatus : ModelingMetadata::StatusInfo { status = ModelingMetadata::StatusKind::open; }
    }
    requirement navigationEntryEvidence : NavigationEntryEvidence;
    dependency navigationEntryEvidenceBasis from navigationEntryEvidence to navigationRules;
    requirement def <'C-031'> OperatorSafetyIntervention {
        doc /* The operator shall intervene when necessary if autonomous safety action is insufficient and intervention is available. */
        comment conditions /* Safety action shall not be delayed to preserve qualification. Operator intervention or motor propulsion ends qualification under C-003/C-004 even when it prevents a violation. */
        metadata workStatus : ModelingMetadata::StatusInfo { status = ModelingMetadata::StatusKind::open; }
    }
    requirement operatorSafetyIntervention : OperatorSafetyIntervention;
    dependency operatorSafetyInterventionBasis from operatorSafetyIntervention to navigationRules;
    requirement def <'C-032'> NavigationAdjudication {
        doc /* The organizer shall record the attempt qualification decision and its supporting reason against the navigation adjudication conditions. */
        comment conditions /* A collision, established navigation-rule breach or unsafe conduct requiring safety intervention disqualifies the attempt. Safety action shall not be delayed to preserve qualification, and the operator shall intervene when necessary if autonomous action is insufficient and intervention is available. Operator intervention or motor propulsion ends qualification under C-003/C-004 even when it prevents a violation. A compliant autonomous avoidance maneuver does not by itself end qualification. The organizer shall adjudicate using retained observations, commands, motion history and independent evidence where available, with a recorded reason. Insufficient evidence leaves qualification unconfirmed; absence of collision alone is not proof of compliance. Entry approval does not waive ongoing obligations. */
        metadata workStatus : ModelingMetadata::StatusInfo { status = ModelingMetadata::StatusKind::open; }
    }
    requirement navigationAdjudication : NavigationAdjudication;
    dependency navigationAdjudicationBasis from navigationAdjudication to navigationRules;

}

package GorgeChallengeVerification {
    doc /* Planned qualification cases, not completed evidence. Virtual regression checks and physical demonstrations are separate evidence streams. */
    verification def OverallLengthVerification {
        metadata plannedInspect : VerificationCases::VerificationMethod { kind = VerificationCases::VerificationMethodKind::inspect; }
        metadata plannedTest : VerificationCases::VerificationMethod { kind = VerificationCases::VerificationMethodKind::test; }
        metadata plannedAnalyze : VerificationCases::VerificationMethod { kind = VerificationCases::VerificationMethodKind::analyze; }
        doc /* Inspect and measure the maximum fore-and-aft extent through all normal rig, steering and equipment configurations. Apply the executable lengthLimit constraint with recorded measurement uncertainty; confirm no unmeasured projection extends beyond the reported envelope. */
        objective acceptance { verify GorgeChallenge::overallLength; }
        return verdict : VerificationCases::VerdictKind = VerificationCases::VerdictKind::inconclusive;
    }
    verification def SafetyCapabilityAbortVerification {
        metadata plannedTest : VerificationCases::VerificationMethod { kind = VerificationCases::VerificationMethodKind::test; }
        doc /* Inject loss of required safety functions, including visibility-driven loss and common-cause faults. Confirm qualification terminates when the function is unavailable; demonstrate continued qualification only when an accepted backup maintains that function. */
        objective acceptance { verify GorgeChallenge::safetyCapabilityAbort; }
        return verdict : VerificationCases::VerdictKind = VerificationCases::VerdictKind::inconclusive;
    }
    verification def AutonomousShoreRecoveryVerification {
        metadata plannedTest : VerificationCases::VerificationMethod { kind = VerificationCases::VerificationMethodKind::test; }
        metadata plannedAnalyze : VerificationCases::VerificationMethod { kind = VerificationCases::VerificationMethodKind::analyze; }
        doc /* From declared course locations and casualty states, remove communications and trigger safety abort. Record recovery initiation, chosen accessible destination, transit and final approach. Assess impaired-sensing collision exposure and consequences independently; a successful transit alone does not accept that residual risk. */
        objective acceptance { verify GorgeChallenge::autonomousShoreRecovery; }
        return verdict : VerificationCases::VerdictKind = VerificationCases::VerdictKind::inconclusive;
    }
    verification def AbortAlertVerification {
        metadata plannedTest : VerificationCases::VerificationMethod { kind = VerificationCases::VerificationMethodKind::test; }
        doc /* Trigger abort with available and unavailable links. Observe immediate transmission attempts with a link, durable queueing without a link and delivery after reconnection. Timing implementation tolerance must be declared before qualification. */
        objective acceptance { verify GorgeChallenge::abortAlert; }
        return verdict : VerificationCases::VerdictKind = VerificationCases::VerdictKind::inconclusive;
    }
    verification def NoLitteringVerification {
        metadata plannedInspect : VerificationCases::VerificationMethod { kind = VerificationCases::VerificationMethodKind::inspect; }
        metadata plannedAnalyze : VerificationCases::VerificationMethod { kind = VerificationCases::VerificationMethodKind::analyze; }
        doc /* Review and demonstrate the linked flotation, major-component retention and capsize recovery cases using the same casualty configuration. Account for every major component at retrieval. */
        objective acceptance { verify GorgeChallenge::noLittering; }
        return verdict : VerificationCases::VerdictKind = VerificationCases::VerdictKind::inconclusive;
    }
    verification def CasualtyFlotationVerification {
        metadata plannedTest : VerificationCases::VerificationMethod { kind = VerificationCases::VerificationMethodKind::test; }
        doc /* Execute the approved flooding and capsize exposure cases with maximum mission load. Observe flotation throughout the course-derived recovery duration. A short static float test cannot substantiate a longer recovery exposure. */
        objective acceptance { verify GorgeChallenge::casualtyFlotation; }
        return verdict : VerificationCases::VerdictKind = VerificationCases::VerdictKind::inconclusive;
    }
    verification def MajorComponentRetentionVerification {
        metadata plannedTest : VerificationCases::VerificationMethod { kind = VerificationCases::VerificationMethodKind::test; }
        metadata plannedInspect : VerificationCases::VerificationMethod { kind = VerificationCases::VerificationMethodKind::inspect; }
        doc /* Inspect rig, ballast and battery retention before and after the same flooding and capsize cases used for flotation. Record attachments and any released debris. */
        objective acceptance { verify GorgeChallenge::majorComponentRetention; }
        return verdict : VerificationCases::VerdictKind = VerificationCases::VerdictKind::inconclusive;
    }
    verification def CapsizeRecoveryVerification {
        metadata plannedTest : VerificationCases::VerificationMethod { kind = VerificationCases::VerificationMethodKind::test; }
        doc /* Release the vessel in the declared capsize orientations with communications disabled and execute shore recovery under the approved current, wind and wave profile. Observe arrival at a retrievable location; remaining inverted is allowed. Motor use must disqualify the attempt. */
        objective acceptance { verify GorgeChallenge::capsizeRecovery; }
        return verdict : VerificationCases::VerdictKind = VerificationCases::VerdictKind::inconclusive;
    }
    verification def UnattachedPassageVerification {
        metadata plannedTest : VerificationCases::VerificationMethod { kind = VerificationCases::VerificationMethodKind::test; }
        metadata plannedAnalyze : VerificationCases::VerificationMethod { kind = VerificationCases::VerificationMethodKind::analyze; }
        doc /* Review timestamped passage records and inject grounding, anchoring, shore attachment and refuge entry. Each ends qualification; safe afloat waiting does not. Missing evidence prevents an affirmative qualification verdict. */
        objective acceptance { verify GorgeChallenge::unattachedPassage; }
        return verdict : VerificationCases::VerdictKind = VerificationCases::VerdictKind::inconclusive;
    }
    verification def OutageAutonomyVerification {
        metadata plannedTest : VerificationCases::VerificationMethod { kind = VerificationCases::VerificationMethodKind::test; }
        doc /* Interrupt communications during healthy passage and verify continued autonomous operation, retained observations and backlog delivery. Separately inject a safety failure during the outage to ensure loss of contact does not inhibit recovery. */
        objective acceptance { verify GorgeChallenge::communicationOutageAutonomy; }
        return verdict : VerificationCases::VerdictKind = VerificationCases::VerdictKind::inconclusive;
    }
    verification def ForecastAdmissionVerification {
        metadata plannedTest : VerificationCases::VerificationMethod { kind = VerificationCases::VerificationMethodKind::test; }
        metadata plannedAnalyze : VerificationCases::VerificationMethod { kind = VerificationCases::VerificationMethodKind::analyze; }
        doc /* Exercise forecast-conditioned launch scenarios covering full passage, waiting and recovery exposure. Reject missing or insufficient forecast coverage. Evaluate the frozen Monte Carlo ensemble and explicit edge cases without treating sample completion fraction as calibrated real-world probability. */
        objective acceptance { verify GorgeChallenge::forecastAdmission; }
        return verdict : VerificationCases::VerdictKind = VerificationCases::VerdictKind::inconclusive;
    }
    verification def WeatherOutageContinuationVerification {
        metadata plannedTest : VerificationCases::VerificationMethod { kind = VerificationCases::VerificationMethodKind::test; }
        doc /* Interrupt weather access with applicable and expired forecasts; independently vary onboard safety capability. Confirm continuation requires both applicable forecast information and preserved safety capability. */
        objective acceptance { verify GorgeChallenge::weatherOutageContinuation; }
        return verdict : VerificationCases::VerdictKind = VerificationCases::VerdictKind::inconclusive;
    }
    verification def CourseRecoveryReserveVerification {
        metadata plannedTest : VerificationCases::VerificationMethod { kind = VerificationCases::VerificationMethodKind::test; }
        metadata plannedAnalyze : VerificationCases::VerificationMethod { kind = VerificationCases::VerificationMethodKind::analyze; }
        doc /* Evaluate route-dependent reserve along the course using installed load evidence, adverse currents, route feasibility and uncertainty. An inaccessible shore, infeasible route or missing input cannot establish a protected reserve. */
        objective acceptance { verify GorgeChallenge::courseRecoveryReserve; }
        return verdict : VerificationCases::VerdictKind = VerificationCases::VerdictKind::inconclusive;
    }
    verification def ReserveAbortVerification {
        metadata plannedTest : VerificationCases::VerificationMethod { kind = VerificationCases::VerificationMethodKind::test; }
        metadata plannedAnalyze : VerificationCases::VerificationMethod { kind = VerificationCases::VerificationMethodKind::analyze; }
        doc /* Inject declining energy and increasing recovery demand along the route. Confirm recovery begins with sufficient reserve for the decision delay, transition and transit rather than only after reserve exhaustion. */
        objective acceptance { verify GorgeChallenge::reserveAbort; }
        return verdict : VerificationCases::VerdictKind = VerificationCases::VerdictKind::inconclusive;
    }
    verification def NightOperationVerification {
        metadata plannedTest : VerificationCases::VerificationMethod { kind = VerificationCases::VerificationMethodKind::test; }
        doc /* Exercise the declared navigation, traffic, communications and recovery scenarios in darkness. Confirm nightfall alone does not terminate qualification. Simulation cannot close optical sensing or navigation-light physical evidence. */
        objective acceptance { verify GorgeChallenge::nightOperation; }
        return verdict : VerificationCases::VerdictKind = VerificationCases::VerdictKind::inconclusive;
    }
    verification def AbortPersistenceVerification {
        metadata plannedTest : VerificationCases::VerificationMethod { kind = VerificationCases::VerificationMethodKind::test; }
        doc /* After abort, test reboot, contact restoration, refuge departure and operator relocation. Qualification remains ended until the new attempt departure-gate condition is met; partial progress is not carried forward. */
        objective acceptance { verify GorgeChallenge::abortPersistence; }
        return verdict : VerificationCases::VerdictKind = VerificationCases::VerdictKind::inconclusive;
    }
    verification def RecoveryConspicuityVerification {
        metadata plannedTest : VerificationCases::VerificationMethod { kind = VerificationCases::VerificationMethodKind::test; }
        metadata plannedInspect : VerificationCases::VerificationMethod { kind = VerificationCases::VerificationMethodKind::inspect; }
        doc /* Inspect and test recovery indications against the deployment-specific navigation-signal matrix in the approved visibility conditions, including the casualty states for which recovery is claimed. */
        objective acceptance { verify GorgeChallenge::recoveryConspicuity; }
        return verdict : VerificationCases::VerdictKind = VerificationCases::VerdictKind::inconclusive;
    }
    verification def WindSportEncounterVerification {
        metadata plannedTest : VerificationCases::VerificationMethod { kind = VerificationCases::VerificationMethodKind::test; }
        metadata plannedAnalyze : VerificationCases::VerificationMethod { kind = VerificationCases::VerificationMethodKind::analyze; }
        doc /* Exercise BlueDogLocationTraffic windsurfCrossing, wingfoilTurn, kiteSweep, fallenRider and groupEncounter across both tacks, overtaking, unknown tack, glare, waves and darkness. Independently record rider/equipment extent, timing, swept-volume clearance and navigation obligations. Include timely, delayed and absent rider avoidance, falls, track swaps and no feasible sailing response. Scripted planar targets or cooperative passes cannot close these cases.*/
        objective acceptance {
            verify GorgeChallenge::trafficCoexistence;
            verify GorgeChallenge::navigationRules;
        }
        return verdict : VerificationCases::VerdictKind = VerificationCases::VerdictKind::inconclusive;
    }
    verification def LocationTrafficAdmissionVerification {
        metadata plannedTest : VerificationCases::VerificationMethod { kind = VerificationCases::VerificationMethodKind::test; }
        metadata plannedAnalyze : VerificationCases::VerificationMethod { kind = VerificationCases::VerificationMethodKind::analyze; }
        doc /* Exercise BlueDogLocationTraffic windowOverrun and WindowAssessment for surveyed sectors and background reaches on both legs, waiting and recovery. Reject missing traffic evidence, unsupported wind/daylight conditions, incomplete coverage and intervals outside reviewed windows. Compare cumulative exposure, energy, sensing and recovery before departure. Sparse heatmaps and zero observed users cannot establish absence. Reassess delays and unexpected traffic; no accepted window yet.*/
        objective acceptance {
            verify GorgeChallenge::forecastAdmission;
        }
        return verdict : VerificationCases::VerdictKind = VerificationCases::VerdictKind::inconclusive;
    }
    verification def NavigationRulesEntryAndAdjudicationVerification {
        metadata plannedInspect : VerificationCases::VerificationMethod { kind = VerificationCases::VerificationMethodKind::inspect; }
        metadata plannedTest : VerificationCases::VerificationMethod { kind = VerificationCases::VerificationMethodKind::test; }
        metadata plannedAnalyze : VerificationCases::VerificationMethod { kind = VerificationCases::VerificationMethodKind::analyze; }
        doc /* Planned case; no completed compliance evidence. Review entry applicability, current rule/notice baseline, installed observation and maneuver evidence, controlled demonstrations and simulation limitations against predeclared criteria. Reject unsupported admitted conditions. Replay compliant autonomous avoidance, no-contact rule breach, collision, operator intervention, motor-assisted safety action and insufficient evidence; confirm their distinct qualification outcomes. Record configuration, conditions, reviewer, evidence and rationale. Do not stage hazardous encounters with uninvolved users.*/
        objective acceptance {
            verify GorgeChallenge::navigationRules;
            verify GorgeChallenge::navigationRuleApplicability;
            verify GorgeChallenge::navigationRuleBaseline;
            verify GorgeChallenge::navigationEntryEvidence;
            verify GorgeChallenge::operatorSafetyIntervention;
            verify GorgeChallenge::navigationAdjudication;
        }
        return verdict : VerificationCases::VerdictKind = VerificationCases::VerdictKind::inconclusive;
    }
    verification def InlandApplicabilityVerification {
        metadata plannedInspect : VerificationCases::VerificationMethod { kind = VerificationCases::VerificationMethodKind::inspect; }
        metadata plannedAnalyze : VerificationCases::VerificationMethod { kind = VerificationCases::VerificationMethodKind::analyze; }
        doc /* Planned case; no completed compliance evidence. Sources: Rules 1-3, https://www.ecfr.gov/current/title-33/chapter-I/subchapter-E/part-83/subpart-A . Review jurisdiction, vessel classification, sailing/powered/casualty modes, responsibility, local provisions and authority for exceptions. Record applicability dispositions; no blanket small-vessel or autonomous exemption.*/
        objective acceptance {
            verify GorgeChallenge::navigationRules;
        }
        return verdict : VerificationCases::VerdictKind = VerificationCases::VerdictKind::inconclusive;
    }
    verification def InlandLookoutAndAvoidanceVerification {
        metadata plannedTest : VerificationCases::VerificationMethod { kind = VerificationCases::VerificationMethodKind::test; }
        metadata plannedAnalyze : VerificationCases::VerificationMethod { kind = VerificationCases::VerificationMethodKind::analyze; }
        doc /* Planned case; no completed compliance evidence. Sources: Rules 5-8, https://www.ecfr.gov/current/title-33/chapter-I/subchapter-E/part-83/subpart-B . Demonstrate installed lookout, safe speed, risk appraisal and effective avoidance under admitted conditions, including uncertain and missed tracks. Independently observe early/substantial action and effectiveness. No-contact outcome alone is insufficient.*/
        objective acceptance {
            verify GorgeChallenge::navigationRules;
        }
        return verdict : VerificationCases::VerdictKind = VerificationCases::VerdictKind::inconclusive;
    }
    verification def InlandEncounterConductVerification {
        metadata plannedTest : VerificationCases::VerificationMethod { kind = VerificationCases::VerificationMethodKind::test; }
        metadata plannedAnalyze : VerificationCases::VerificationMethod { kind = VerificationCases::VerificationMethodKind::analyze; }
        doc /* Planned case; no completed compliance evidence. Sources: Rules 11-18, https://www.ecfr.gov/current/title-33/chapter-I/subchapter-E/part-83/subpart-B . Review applicability and demonstrate sailing, overtaking, crossing/head-on where relevant, give-way and stand-on escalation, unknown tack and exceptional status. Retain overtaking duty until past and clear. Distinguish permission from mandatory action; a subset does not verify omitted rules.*/
        objective acceptance {
            verify GorgeChallenge::navigationRules;
        }
        return verdict : VerificationCases::VerdictKind = VerificationCases::VerdictKind::inconclusive;
    }
    verification def InlandChannelAndVisibilityVerification {
        metadata plannedTest : VerificationCases::VerificationMethod { kind = VerificationCases::VerificationMethodKind::test; }
        metadata plannedAnalyze : VerificationCases::VerificationMethod { kind = VerificationCases::VerificationMethodKind::analyze; }
        doc /* Planned case; no completed compliance evidence. Sources: Rules 9, 10 and 19, https://www.ecfr.gov/current/title-33/chapter-I/subchapter-E/part-83/subpart-B . Review channel confinement, nonimpediment, crossings, applicable traffic separation and restricted visibility. Exercise simultaneous pairwise/channel duties. Record applicability or justified exclusions, operating limits and response to deteriorating visibility. In-sight logic does not verify nonvisual encounters.*/
        objective acceptance {
            verify GorgeChallenge::navigationRules;
        }
        return verdict : VerificationCases::VerdictKind = VerificationCases::VerdictKind::inconclusive;
    }
    verification def InlandSignalsVerification {
        metadata plannedTest : VerificationCases::VerificationMethod { kind = VerificationCases::VerificationMethodKind::test; }
        metadata plannedInspect : VerificationCases::VerificationMethod { kind = VerificationCases::VerificationMethodKind::inspect; }
        doc /* Planned case; no completed compliance evidence. Sources: Rules 20-37 and applicable annexes, https://www.ecfr.gov/current/title-33/chapter-I/subchapter-E . Review lights, shapes and sound signals for sailing, powered recovery and casualty modes. Demonstrate required equipment performance and signal behavior under admitted conditions. Record authority for alternatives; review distress signaling and applicable exemptions separately.*/
        objective acceptance {
            verify GorgeChallenge::navigationRules;
        }
        return verdict : VerificationCases::VerdictKind = VerificationCases::VerdictKind::inconclusive;
    }
    verification def PassageQualificationVerification {
        metadata plannedTest : VerificationCases::VerificationMethod { kind = VerificationCases::VerificationMethodKind::test; }
        metadata plannedAnalyze : VerificationCases::VerificationMethod { kind = VerificationCases::VerificationMethodKind::analyze; }
        doc /* Review the approved course, configuration and predeclared admission evidence, then independently reconstruct the ordered finite gate crossings and complete attempt history. Exercise skipped/reversed/touched gates, operator updates, motor thrust, grounding and restart. A complete circuit is insufficient when another governing challenge obligation failed or evidence is missing. Safe unassisted righting preserves qualification only with required safety capability; recovery after disqualification cannot transfer partial progress into a new attempt. Accept C-000 only after every applicable C-001, C-003 through C-010 and C-012 through C-027 obligation has its own accepted evidence or justified coverage in the same attempt. */
        objective acceptance {
            verify GorgeChallenge::transGorgeChallenge;
            verify GorgeChallenge::courseCompletion;
            verify GorgeChallenge::unassistedAttempt;
            verify GorgeChallenge::sailingPropulsion;
        }
        return verdict : VerificationCases::VerdictKind = VerificationCases::VerdictKind::inconclusive;
    }
    verification def ObservationAndInterventionVerification {
        metadata plannedTest : VerificationCases::VerificationMethod { kind = VerificationCases::VerificationMethodKind::test; }
        doc /* Measure acquisition-to-shore delivery under an available link, including current position, operating mode and health. Interrupt and restore the link; inspect durable backlog replay and continued autonomous control. Exercise authenticated emergency abort and manual-control commands with independent observation of the commanded response and persistent disqualification. Passive monitoring must not change mission state. Distinguish an unavailable link from a failed delivery on an available link. The demonstration must cover the installed vessel and shore endpoints; software queue tests alone do not establish communication service. */
        objective acceptance {
            verify GorgeChallenge::liveObservation;
            verify GorgeChallenge::emergencyIntervention;
        }
        return verdict : VerificationCases::VerdictKind = VerificationCases::VerdictKind::inconclusive;
    }
    verification def RestrictedWatersVerification {
        metadata plannedInspect : VerificationCases::VerificationMethod { kind = VerificationCases::VerificationMethodKind::inspect; }
        metadata plannedTest : VerificationCases::VerificationMethod { kind = VerificationCases::VerificationMethodKind::test; }
        metadata plannedAnalyze : VerificationCases::VerificationMethod { kind = VerificationCases::VerificationMethodKind::analyze; }
        doc /* Review the applicable chart, dam and lock exclusions, local restrictions and current notice baseline for the configured course. Independently compare the complete observed vessel envelope and position uncertainty against approved exclusion geometry throughout the attempt. Exercise approach, navigation-loss and no-feasible-maneuver cases in a controlled test or simulation; do not enter prohibited waters to test the response. A route-planner clearance result is supporting analysis, not evidence that actual operation remained outside restrictions. */
        objective acceptance { verify GorgeChallenge::restrictedWaters; }
        return verdict : VerificationCases::VerdictKind = VerificationCases::VerdictKind::inconclusive;
    }
}

package BlueDogSatisfaction {
    private import BlueDogRequirements::*;
    private import BlueDog::Architecture::missionContext;
    doc /* Candidate design satisfaction assertions, not verification evidence. Physical
     * implementation, quantitative acceptance, and verification remain open.
     * Regulatory classification is a project process obligation, not assigned
     * to a component as though hardware alone could establish authorization.
     */
    satisfy BlueDogRequirements::transportability by missionContext.boat.hullAndRig.handling;
    satisfy BlueDogRequirements::desktopManufacture by missionContext.boat.hullAndRig.printedHull;
    satisfy BlueDogRequirements::serviceability by missionContext.boat;
    satisfy BlueDogRequirements::trafficSafety by missionContext.boat;
    satisfy BlueDogRequirements::operatingBoundary by BlueDogLogicalArchitecture::vessel.boundary;
    satisfy BlueDogRequirements::emergencyControl by missionContext.boat;
    satisfy BlueDogRequirements::navigationConspicuity by missionContext.boat.signaling;
    satisfy BlueDogRequirements::environmentalEnvelope by missionContext.boat;
    satisfy BlueDogRequirements::marineDurability by missionContext.boat;
    satisfy BlueDogRequirements::capsizeResilience by missionContext.boat;
    satisfy BlueDogRequirements::recoveryPropulsion by missionContext.boat;
    satisfy BlueDogRequirements::recoveryEnergy by missionContext.boat;
    satisfy BlueDogRequirements::telemetryEquipment by missionContext.shoreSupport.monitoringStation;
    satisfy BlueDogRequirements::commandIntegrity by missionContext.boat.communications.commandGateway;
    satisfy BlueDogRequirements::roundTrip by missionContext.boat;
    satisfy BlueDogRequirements::multiDayEndurance by missionContext.boat;
    satisfy BlueDogRequirements::energyAwareness by BlueDogLogicalArchitecture::vessel.energy;
    satisfy BlueDogRequirements::navigationAndControl by missionContext.boat;
    satisfy BlueDogRequirements::resetRecovery by missionContext.boat;
    satisfy BlueDogRequirements::lowEnergyRecovery by missionContext.boat;
    satisfy BlueDogRequirements::communications by missionContext.boat;
    satisfy BlueDogRequirements::ingressResponse by missionContext.boat;
    satisfy BlueDogRequirements::missionEvidence by missionContext.boat;
    satisfy BlueDogRequirements::gorgeEnvironment by missionContext.boat;
    satisfy BlueDogRequirements::gorgeWind by missionContext.boat;
    satisfy BlueDogRequirements::gorgeWaves by missionContext.boat;
    satisfy BlueDogRequirements::gorgeCurrent by missionContext.boat;
    satisfy BlueDogRequirements::gorgeSurvivalWind by missionContext.boat;
    satisfy BlueDogRequirements::gorgeSurvivalWaves by missionContext.boat;
    satisfy BlueDogRequirements::airTemperature by missionContext.boat;
    satisfy BlueDogRequirements::waterTemperature by missionContext.boat;
    satisfy BlueDogRequirements::humidity by missionContext.boat;
    satisfy BlueDogRequirements::visibility by missionContext.boat;
    satisfy BlueDogRequirements::calmOperation by missionContext.boat;
    satisfy BlueDogRequirements::envelopeTransition by missionContext.boat;
    satisfy BlueDogRequirements::freshwaterExposure by missionContext.boat;
    satisfy BlueDogRequirements::enclosureSealing by missionContext.boat.hullAndRig.enclosure;
    satisfy BlueDogRequirements::wetMechanicalIntegrity by missionContext.boat.hullAndRig;
    satisfy BlueDogRequirements::wetElectricalIntegrity by missionContext.boat;
    satisfy BlueDogRequirements::solarHeating by BlueDogLogicalArchitecture::vessel.energy;
    satisfy BlueDogRequirements::printedMaterialAging by missionContext.boat.hullAndRig.printedHull;
    satisfy BlueDogRequirements::selfRighting by missionContext.boat;
    satisfy BlueDogRequirements::capsizeControlRecovery by missionContext.boat;
    satisfy BlueDogRequirements::submergedWeedPassage by missionContext.boat;
    satisfy BlueDogRequirements::weedSnagShedding by missionContext.boat;
    satisfy BlueDogRequirements::weedBlockageResponse by missionContext.boat;
    satisfy BlueDogRequirements::recoveryPropulsorWeeds by missionContext.boat;
    satisfy BlueDogRequirements::navigationAvailability by missionContext.boat.navigation;
    satisfy BlueDogRequirements::launchEnergyAdmission by BlueDogLogicalArchitecture::vessel.energy;
    satisfy BlueDogRequirements::challengeMotorInhibition by BlueDogLogicalArchitecture::vessel.recovery;

    // Candidate satisfaction assertions for acceptance leaves; evidence remains open.
    satisfy BlueDogRequirements::energyEstimateCadence by BlueDogLogicalArchitecture::vessel.energy;
    satisfy BlueDogRequirements::reserveEstimateCadence by BlueDogLogicalArchitecture::vessel.energy;
    satisfy BlueDogRequirements::energyEstimateAccuracy by BlueDogLogicalArchitecture::vessel.energy;
    satisfy BlueDogRequirements::conservativeEnergyEstimate by BlueDogLogicalArchitecture::vessel.energy;
    satisfy BlueDogRequirements::guidanceUpdateCadence by missionContext.boat.control;
    satisfy BlueDogRequirements::sailCommandCadence by BlueDogLogicalArchitecture::vessel.actuation;
    satisfy BlueDogRequirements::steeringCommandCadence by BlueDogLogicalArchitecture::vessel.actuation;
    satisfy BlueDogRequirements::positionAccuracy by BlueDogLogicalArchitecture::vessel.navigation;
    satisfy BlueDogRequirements::headingAccuracy by BlueDogLogicalArchitecture::vessel.navigation;
    satisfy BlueDogRequirements::restartDeadline by BlueDogLogicalArchitecture::vessel.recovery;
    satisfy BlueDogRequirements::missionStateRestoration by missionContext.boat.control;
    satisfy BlueDogRequirements::gateProgressRestoration by missionContext.boat.control;
    satisfy BlueDogRequirements::resetRestrictionPreservation by missionContext.boat.control;
    satisfy BlueDogRequirements::lowEnergyEntry by BlueDogLogicalArchitecture::vessel.energy;
    satisfy BlueDogRequirements::lowEnergyPayloadInhibition by BlueDogLogicalArchitecture::vessel.energy;
    satisfy BlueDogRequirements::lowEnergyNavigationContinuity by missionContext.boat.control;
    satisfy BlueDogRequirements::lowEnergyCollisionContinuity by BlueDogLogicalArchitecture::vessel.collision;
    satisfy BlueDogRequirements::lowEnergyExit by BlueDogLogicalArchitecture::vessel.energy;
    satisfy BlueDogRequirements::payloadRestartPermission by BlueDogLogicalArchitecture::vessel.energy;
    satisfy BlueDogRequirements::telemetryDeliveryCadence by BlueDogLogicalArchitecture::vessel.communications;
    satisfy BlueDogRequirements::outageAutonomy by missionContext.boat.control;
    satisfy BlueDogRequirements::reconnectCurrentRecord by BlueDogLogicalArchitecture::vessel.communications;
    satisfy BlueDogRequirements::backlogOrdering by BlueDogLogicalArchitecture::vessel.communications;
    satisfy BlueDogRequirements::backlogCurrentPriority by BlueDogLogicalArchitecture::vessel.communications;
    satisfy BlueDogRequirements::ingressDetection by missionContext.boat.recovery.ingressMonitor;
    satisfy BlueDogRequirements::ingressRecoveryRequest by BlueDogLogicalArchitecture::vessel.recovery;
    satisfy BlueDogRequirements::ingressFlotation by missionContext.boat.hullAndRig;
    satisfy BlueDogRequirements::ingressElectronicsProtection by missionContext.boat.hullAndRig.enclosure;
    satisfy BlueDogRequirements::ingressPositionContinuity by BlueDogLogicalArchitecture::vessel.communications;
    satisfy BlueDogRequirements::periodicLogCadence by BlueDogLogicalArchitecture::vessel.recording;
    satisfy BlueDogRequirements::logRetention by BlueDogLogicalArchitecture::vessel.recording;
    satisfy BlueDogRequirements::criticalEventRecording by BlueDogLogicalArchitecture::vessel.recording;
    satisfy BlueDogRequirements::logTimestampAccuracy by BlueDogLogicalArchitecture::vessel.recording;
    satisfy BlueDogRequirements::invalidTimestampMarking by BlueDogLogicalArchitecture::vessel.recording;
    satisfy BlueDogRequirements::logGapIndication by BlueDogLogicalArchitecture::vessel.recording;
    satisfy BlueDogRequirements::logInterruptionDurability by BlueDogLogicalArchitecture::vessel.recording;
    satisfy BlueDogRequirements::reconnectLogPreservation by BlueDogLogicalArchitecture::vessel.recording;
    satisfy BlueDogRequirements::qualificationPersistence by BlueDogLogicalArchitecture::vessel.supervision;
    satisfy BlueDogRequirements::unknownQualificationFallback by BlueDogLogicalArchitecture::vessel.supervision;
    satisfy BlueDogRequirements::navigationValidEpochs by missionContext.boat.navigation;
    satisfy BlueDogRequirements::staleNavigationInvalidation by missionContext.boat.navigation;
    satisfy BlueDogRequirements::navigationDegradedTransition by missionContext.boat.control;
    satisfy BlueDogRequirements::staleNavigationUseInhibition by missionContext.boat.control;
    satisfy BlueDogRequirements::soloTransport by missionContext.boat.hullAndRig.handling;
    satisfy BlueDogRequirements::liftMass by missionContext.boat.hullAndRig.handling;
    satisfy BlueDogRequirements::setupDuration by missionContext.boat.hullAndRig.handling;
    satisfy BlueDogRequirements::packDuration by missionContext.boat.hullAndRig.handling;
    satisfy BlueDogRequirements::soloLaunch by missionContext.boat.hullAndRig.handling;
    satisfy BlueDogRequirements::soloRetrieval by missionContext.boat.hullAndRig.handling;
    satisfy BlueDogRequirements::replacementDuration by missionContext.boat;
    satisfy BlueDogRequirements::nondestructiveService by missionContext.boat;
    satisfy BlueDogRequirements::postServiceSealing by missionContext.boat.hullAndRig.enclosure;
    satisfy BlueDogRequirements::postServiceActuation by BlueDogLogicalArchitecture::vessel.actuation;
    satisfy BlueDogRequirements::trafficTracking by BlueDogLogicalArchitecture::vessel.trafficObservation;
    satisfy BlueDogRequirements::collisionAssessmentCadence by BlueDogLogicalArchitecture::vessel.collision;
    satisfy BlueDogRequirements::avoidanceCommandDeadline by BlueDogLogicalArchitecture::vessel.collision;
    satisfy BlueDogRequirements::trafficAwarenessFault by BlueDogLogicalArchitecture::vessel.collision;
    satisfy BlueDogRequirements::boundaryEvaluationCadence by BlueDogLogicalArchitecture::vessel.boundary;
    satisfy BlueDogRequirements::boundaryAvoidanceDeadline by BlueDogLogicalArchitecture::vessel.boundary;
    satisfy BlueDogRequirements::boundaryAvoidanceRecording by BlueDogLogicalArchitecture::vessel.recording;
    satisfy BlueDogRequirements::boundaryStartInhibition by BlueDogLogicalArchitecture::vessel.boundary;
    satisfy BlueDogRequirements::boundaryDegradedEvidence by BlueDogLogicalArchitecture::vessel.boundary;
    satisfy BlueDogRequirements::abortLatchDeadline by BlueDogLogicalArchitecture::vessel.recovery;
    satisfy BlueDogRequirements::recoveryTelemetryCadence by BlueDogLogicalArchitecture::vessel.communications;
    satisfy BlueDogRequirements::motorIsolationDeadline by missionContext.boat.recovery.motorSystem;
    satisfy BlueDogRequirements::isolationRestartInhibition by missionContext.boat.recovery.motorSystem;
    satisfy BlueDogRequirements::manualControlLossShutdown by BlueDogLogicalArchitecture::vessel.recovery;
    satisfy BlueDogRequirements::controlLossLocationContinuity by BlueDogLogicalArchitecture::vessel.communications;
    satisfy BlueDogRequirements::navigationLightPresentation by missionContext.boat.signaling;
    satisfy BlueDogRequirements::navigationShapePresentation by missionContext.boat.signaling;
    satisfy BlueDogRequirements::navigationSoundPresentation by missionContext.boat.signaling;
    satisfy BlueDogRequirements::signalingModeDeadline by missionContext.boat.signaling;
    satisfy BlueDogRequirements::signalingFaultRecording by BlueDogLogicalArchitecture::vessel.recording;
    satisfy BlueDogRequirements::signalingFaultReporting by BlueDogLogicalArchitecture::vessel.communications;
    satisfy BlueDogRequirements::telemetryDisplayContent by missionContext.shoreSupport.monitoringStation;
    satisfy BlueDogRequirements::telemetryStaleIndication by missionContext.shoreSupport.monitoringStation;
    satisfy BlueDogRequirements::telemetryIdentityPreservation by missionContext.shoreSupport.monitoringStation;
    satisfy BlueDogRequirements::telemetryDuplicateSuppression by missionContext.shoreSupport.monitoringStation;
    satisfy BlueDogRequirements::unauthenticatedCommandRejection by missionContext.boat.communications.commandGateway;
    satisfy BlueDogRequirements::replayCommandRejection by missionContext.boat.communications.commandGateway;
    satisfy BlueDogRequirements::expiredCommandRejection by missionContext.boat.communications.commandGateway;
    satisfy BlueDogRequirements::acceptedCommandDeadline by missionContext.boat.communications.commandGateway;
    satisfy BlueDogRequirements::onboardAcknowledgmentDeadline by missionContext.boat.communications.commandGateway;
    satisfy BlueDogRequirements::acknowledgmentQueueing by missionContext.boat.communications.commandGateway;
    satisfy BlueDogRequirements::externalControlDisqualification by BlueDogLogicalArchitecture::vessel.supervision;
    satisfy BlueDogRequirements::visibilityNavigationCapability by missionContext.boat.navigation;
    satisfy BlueDogRequirements::visibilityTrafficCapability by BlueDogLogicalArchitecture::vessel.trafficObservation;
    satisfy BlueDogRequirements::restrictedVisibilityEntry by missionContext.boat.control;
    satisfy BlueDogRequirements::restrictedVisibilityEvidence by BlueDogLogicalArchitecture::vessel.recording;
    satisfy BlueDogRequirements::restrictedVisibilityCollisionAssessment by BlueDogLogicalArchitecture::vessel.collision;
    satisfy BlueDogRequirements::survivalEntryDeadline by missionContext.boat.control;
    satisfy BlueDogRequirements::survivalTransitionRecording by BlueDogLogicalArchitecture::vessel.recording;
    satisfy BlueDogRequirements::sailingResumptionDeadline by missionContext.boat.control;
    satisfy BlueDogRequirements::sailingResumptionInhibition by missionContext.boat.control;
    satisfy BlueDogRequirements::resumptionBlockEvidence by BlueDogLogicalArchitecture::vessel.recording;
    satisfy BlueDogRequirements::wetMechanismTravel by missionContext.boat.hullAndRig;
    satisfy BlueDogRequirements::wetJointIntegrity by missionContext.boat.hullAndRig;
    satisfy BlueDogRequirements::wetConductorResistance by missionContext.boat.energy;
    satisfy BlueDogRequirements::wetInsulationResistance by missionContext.boat.energy;
    satisfy BlueDogRequirements::hotSunElectronicsOperation by missionContext.boat;
    satisfy BlueDogRequirements::hotSunBatteryTemperature by missionContext.boat.energy.storage;
    satisfy BlueDogRequirements::batteryChargeTemperatureInhibition by BlueDogLogicalArchitecture::vessel.energy;
    satisfy BlueDogRequirements::rightingDeadline by missionContext.boat.hullAndRig;
    satisfy BlueDogRequirements::capsizeRigRetention by missionContext.boat.hullAndRig;
    satisfy BlueDogRequirements::capsizeBallastRetention by missionContext.boat.hullAndRig.keelAndBallast;
    satisfy BlueDogRequirements::capsizeElectronicsSealing by missionContext.boat.hullAndRig.enclosure;
    satisfy BlueDogRequirements::controlRecoveryDeadline by missionContext.boat.control;
    satisfy BlueDogRequirements::capsizeGateProgressRetention by BlueDogLogicalArchitecture::vessel.supervision;
    satisfy BlueDogRequirements::capsizeQualificationRetention by BlueDogLogicalArchitecture::vessel.supervision;
    satisfy BlueDogRequirements::capsizeRestrictionRetention by BlueDogLogicalArchitecture::vessel.supervision;
    satisfy BlueDogRequirements::weedPassageSpeed by missionContext.boat;
    satisfy BlueDogRequirements::weedPassageSteering by BlueDogLogicalArchitecture::vessel.actuation;
    satisfy BlueDogRequirements::weedSnagSpeedRecovery by missionContext.boat;
    satisfy BlueDogRequirements::weedSnagSteeringRecovery by BlueDogLogicalArchitecture::vessel.actuation;
    satisfy BlueDogRequirements::weedBlockageFault by BlueDogLogicalArchitecture::vessel.recording;
    satisfy BlueDogRequirements::weedBlockageContingency by missionContext.boat.control;
    satisfy BlueDogRequirements::weedBlockageLocation by BlueDogLogicalArchitecture::vessel.communications;
    satisfy BlueDogRequirements::poweredWeedSpeed by missionContext.boat.recovery.motorSystem;
    satisfy BlueDogRequirements::poweredWeedCurrent by missionContext.boat.recovery.motorSystem;
    satisfy BlueDogRequirements::poweredWeedTemperature by missionContext.boat.recovery.motorSystem;
    satisfy BlueDogRequirements::lockedPropulsorShutdown by missionContext.boat.recovery.motorSystem;
    satisfy BlueDogRequirements::motorQualificationInvariant by BlueDogLogicalArchitecture::vessel.supervision;
    satisfy BlueDogRequirements::freshRecoveryCommand by BlueDogLogicalArchitecture::vessel.recovery;
    satisfy BlueDogRequirements::ingressEventDeadline by BlueDogLogicalArchitecture::vessel.recording;
    satisfy BlueDogRequirements::qualificationRestoration by BlueDogLogicalArchitecture::vessel.supervision;
    satisfy BlueDogRequirements::sustainedReserveProtection by missionContext.boat.energy;
    satisfy BlueDogRequirements::peakSupplyCapability by missionContext.boat.energy;
    satisfy BlueDogRequirements::cruisePerformance by missionContext.boat;
    satisfy BlueDogRequirements::legProgress by missionContext.boat;
    satisfy BlueDogRequirements::passageDuration by missionContext.boat;
    satisfy BlueDogRequirements::missionReliability by missionContext.boat;
    satisfy BlueDogRequirements::missionSuccessProbability by missionContext.boat;
    satisfy BlueDogRequirements::failureRateBudget by missionContext.boat;
    satisfy BlueDogRequirements::windObservation by BlueDogLogicalArchitecture::vessel.wind;
    satisfy BlueDogRequirements::windSampleCadence by BlueDogLogicalArchitecture::vessel.wind;
    satisfy BlueDogRequirements::windSpeedAccuracy by BlueDogLogicalArchitecture::vessel.wind;
    satisfy BlueDogRequirements::windDirectionAccuracy by BlueDogLogicalArchitecture::vessel.wind;
    satisfy BlueDogRequirements::windStaleInvalidation by BlueDogLogicalArchitecture::vessel.wind;
    satisfy BlueDogRequirements::invalidWindUseInhibition by missionContext.boat.control;
    satisfy BlueDogRequirements::windLossResponse by missionContext.boat.control;
    satisfy BlueDogRequirements::windSensingEndurance by BlueDogLogicalArchitecture::vessel.wind;

    // System responsibility allocations for the finite Gorge challenge.
    // These assert intended design responsibility, not demonstrated compliance.
    satisfy GorgeChallenge::overallLength by missionContext.boat;
    satisfy GorgeChallenge::safetyCapabilityAbort by BlueDogLogicalArchitecture::vessel.recovery;
    satisfy GorgeChallenge::autonomousShoreRecovery by BlueDogLogicalArchitecture::vessel.recovery;
    satisfy GorgeChallenge::abortAlert by BlueDogLogicalArchitecture::vessel.communications;
    satisfy GorgeChallenge::noLittering by missionContext.boat;
    satisfy GorgeChallenge::casualtyFlotation by missionContext.boat.hullAndRig;
    satisfy GorgeChallenge::majorComponentRetention by missionContext.boat.hullAndRig;
    satisfy GorgeChallenge::capsizeRecovery by missionContext.boat;
    satisfy GorgeChallenge::unattachedPassage by BlueDogLogicalArchitecture::vessel.supervision;
    satisfy GorgeChallenge::communicationOutageAutonomy by BlueDogLogicalArchitecture::vessel.supervision;
    satisfy GorgeChallenge::forecastAdmission by BlueDogLogicalArchitecture::vessel.supervision;
    satisfy GorgeChallenge::weatherOutageContinuation by BlueDogLogicalArchitecture::vessel.supervision;
    satisfy GorgeChallenge::courseRecoveryReserve by BlueDogLogicalArchitecture::vessel.energy;
    satisfy GorgeChallenge::reserveAbort by BlueDogLogicalArchitecture::vessel.recovery;
    satisfy GorgeChallenge::nightOperation by missionContext.boat;
    satisfy GorgeChallenge::abortPersistence by BlueDogLogicalArchitecture::vessel.recovery;
    satisfy GorgeChallenge::recoveryConspicuity by missionContext.boat.signaling;
    satisfy BlueDogRequirements::vegetationResilience by missionContext.boat;
}

package BlueDogArchitectureContracts {
    private import ScalarValues::*;
    doc /* Project allocation conventions, not a new relationship engine.
     * Primary/recovery label implementation paths, not automatic mode selection
     * or proof of independent operation. Each mapping is a provisional claim. */
    enum def ImplementationPath { primary; recovery; shared; }
    allocation def ContextMapping {
        end part context;
        end part logical;
        attribute scope : String;
    }
    allocation def IC01Responsibility {
        end part logical;
        end part implementation;
        ref part configuration : MarineDesign::Design = BlueDogIC01::design;
        attribute path : ImplementationPath;
        attribute scope : String;
    }
    allocation def IC01Exchange {
        end occurrence logical;
        end occurrence implementation;
        ref part configuration : MarineDesign::Design = BlueDogIC01::design;
        attribute path : ImplementationPath;
        attribute scope : String;
        doc /* Map a logical transfer to a candidate transfer. A common payload
         * definition preserves meaning; latency, arbitration, encoding and
         * installed protocol remain interface decisions, not implied by this link. */
    }
    allocation def IC01InternalExchange {
        end occurrence logical;
        end part implementation;
        ref part configuration : MarineDesign::Design = BlueDogIC01::design;
        attribute path : ImplementationPath;
        attribute scope : String;
        doc /* Interaction between responsibilities allocated to one controller.
         * This records an internal implementation obligation, not an existing
         * software call or measured scheduling/latency guarantee. */
    }
}

package BlueDogArchitectureCorrespondence {
    private import BlueDogArchitectureContracts::*;
    private import BlueDogLogicalArchitecture::vessel;
    private import BlueDogPhysicalArchitecture::ic01;
    private import BlueDog::Architecture::missionContext;
    doc /* Cross-description mappings for the finite-Gorge IC-01 hypothesis.
     * Logical/implementation allocation can be many-to-many. The scope on each
     * link identifies the contribution; no allocation asserts physical acceptance.
     * Source configurations and historical evidence retain their own identity. */
    metadata workStatus : ModelingMetadata::StatusInfo { status = ModelingMetadata::StatusKind::open; }
    metadata interfaceDecisions : ModelingMetadata::Issue {
        text = "Resolve sensor freshness and validity propagation; peer timeout, authority arbitration and startup after primary loss; independent inverted safety observations; controller software deployment and timing; recording/telemetry power, retention and arbitration. Existing IC-01 mass and energy allowances are hypotheses, not a bill of materials or installed-load evidence.";
    }
    metadata contextLimits : ModelingMetadata::Issue {
        text = "Navigation signaling has a context responsibility and requirements but no detailed logical interface or IC-01 equipment allocation. Optional observation payload and future harvesting remain outside this finite-Gorge implementation. Hull/rig composition and operator launch/pickup stay in their physical and human descriptions; they are not fictitious controller functions.";
    }
    allocation contextEnergy : ContextMapping allocate missionContext.boat.energy to vessel.energy { attribute :>> scope = "Reserve estimation and protection"; }
    allocation contextNavigation : ContextMapping allocate missionContext.boat.navigation to vessel.navigation { attribute :>> scope = "Position and attitude estimation"; }
    allocation contextWind : ContextMapping allocate missionContext.boat.navigation to vessel.wind { attribute :>> scope = "Apparent wind estimates"; }
    allocation contextTrafficObservation : ContextMapping allocate missionContext.boat.navigation to vessel.trafficObservation { attribute :>> scope = "Traffic observations"; }
    allocation contextSupervision : ContextMapping allocate missionContext.boat.control to vessel.supervision { attribute :>> scope = "Permissions and qualification state"; }
    allocation contextGuidance : ContextMapping allocate missionContext.boat.control to vessel.guidance { attribute :>> scope = "Sailing commands"; }
    allocation contextCollision : ContextMapping allocate missionContext.boat.control to vessel.collision { attribute :>> scope = "Encounter assessment"; }
    allocation contextBoundary : ContextMapping allocate missionContext.boat.control to vessel.boundary { attribute :>> scope = "Operating domain assessment"; }
    allocation contextActuation : ContextMapping allocate missionContext.boat.actuation to vessel.actuation { attribute :>> scope = "Sail and steering execution"; }
    allocation contextCommunications : ContextMapping allocate missionContext.boat.communications to vessel.communications { attribute :>> scope = "Onboard telemetry and link status"; }
    allocation contextSafety : ContextMapping allocate missionContext.boat.recovery to vessel.safety { attribute :>> scope = "Required safety capability assessment"; }
    allocation contextRecovery : ContextMapping allocate missionContext.boat.recovery to vessel.recovery { attribute :>> scope = "Shore recovery planning and control"; }
    allocation contextRecoveryActuation : ContextMapping allocate missionContext.boat.recovery to vessel.recoveryActuation { attribute :>> scope = "Recovery propulsion execution"; }
    allocation contextRecording : ContextMapping allocate missionContext.boat.recording to vessel.recording { attribute :>> scope = "Mission evidence retention and readback"; }
    allocation primaryNavigation : IC01Responsibility allocate vessel.navigation to ic01.primaryNavigation {
        attribute :>> path = ImplementationPath::primary;
        attribute :>> scope = "Acquire and supply primary time-stamped navigation estimates";
    }
    allocation recoveryNavigation : IC01Responsibility allocate vessel.navigation to ic01.recoveryNavigation {
        attribute :>> path = ImplementationPath::recovery;
        attribute :>> scope = "Acquire and supply recovery-path navigation estimates";
    }
    allocation primaryNavigationValidation : IC01Responsibility allocate vessel.navigation to ic01.primaryController {
        attribute :>> path = ImplementationPath::primary;
        attribute :>> scope = "Validate and consume primary navigation estimates; stale data cannot become confirmed safety";
    }
    allocation recoveryNavigationValidation : IC01Responsibility allocate vessel.navigation to ic01.recoveryController {
        attribute :>> path = ImplementationPath::recovery;
        attribute :>> scope = "Validate recovery navigation independently of the primary estimate";
    }
    allocation wind : IC01Responsibility allocate vessel.wind to ic01.windSensor {
        attribute :>> path = ImplementationPath::primary;
        attribute :>> scope = "Supply apparent wind estimates with timestamp and validity";
    }
    allocation primarySafety : IC01Responsibility allocate vessel.safety to ic01.primaryController {
        attribute :>> path = ImplementationPath::primary;
        attribute :>> scope = "Assess primary safety capability from observations; inverted evidence remains unresolved";
    }
    allocation recoverySafety : IC01Responsibility allocate vessel.safety to ic01.recoveryController {
        attribute :>> path = ImplementationPath::recovery;
        attribute :>> scope = "Assess recovery safety capability; a peer report alone does not establish independence";
    }
    allocation primaryEnergy : IC01Responsibility allocate vessel.energy to ic01.primaryController {
        attribute :>> path = ImplementationPath::primary;
        attribute :>> scope = "Estimate main and recovery reserve and protect recovery energy";
    }
    allocation recoveryEnergy : IC01Responsibility allocate vessel.energy to ic01.recoveryController {
        attribute :>> path = ImplementationPath::recovery;
        attribute :>> scope = "Assess recovery-bank energy and route demand after primary loss";
    }
    allocation primaryCollision : IC01Responsibility allocate vessel.collision to ic01.primaryController {
        attribute :>> path = ImplementationPath::primary;
        attribute :>> scope = "Assess traffic for sailing";
    }
    allocation recoveryCollision : IC01Responsibility allocate vessel.collision to ic01.recoveryController {
        attribute :>> path = ImplementationPath::recovery;
        attribute :>> scope = "Assess traffic for powered recovery; implemented navigation-rule coverage remains open";
    }
    allocation primaryBoundary : IC01Responsibility allocate vessel.boundary to ic01.primaryController {
        attribute :>> path = ImplementationPath::primary;
        attribute :>> scope = "Assess the configured sailing domain";
    }
    allocation recoveryBoundary : IC01Responsibility allocate vessel.boundary to ic01.recoveryController {
        attribute :>> path = ImplementationPath::recovery;
        attribute :>> scope = "Assess recovery route boundaries and permitted shore approach";
    }
    allocation primaryObservation : IC01Responsibility allocate vessel.trafficObservation to ic01.primaryObservation {
        attribute :>> path = ImplementationPath::primary;
        attribute :>> scope = "Acquire primary traffic tracks; detection coverage remains unverified";
    }
    allocation recoveryObservation : IC01Responsibility allocate vessel.trafficObservation to ic01.recoveryObservation {
        attribute :>> path = ImplementationPath::recovery;
        attribute :>> scope = "Acquire recovery traffic tracks including the unresolved inverted installation";
    }
    allocation primarySupervision : IC01Responsibility allocate vessel.supervision to ic01.primaryController {
        attribute :>> path = ImplementationPath::primary;
        attribute :>> scope = "Sailing and gate permissions, qualification and abort state";
    }
    allocation recoverySupervision : IC01Responsibility allocate vessel.supervision to ic01.recoveryController {
        attribute :>> path = ImplementationPath::recovery;
        attribute :>> scope = "Recovery-side qualification restrictions and fallback authority; primary-loss arbitration remains open";
    }
    allocation guidance : IC01Responsibility allocate vessel.guidance to ic01.primaryController {
        attribute :>> path = ImplementationPath::primary;
        attribute :>> scope = "Select sailing guidance subject to current permissions";
    }
    allocation sailingActuation : IC01Responsibility allocate vessel.actuation to ic01.sailingActuators {
        attribute :>> path = ImplementationPath::primary;
        attribute :>> scope = "Execute permitted sailing commands";
    }
    allocation recoveryManagement : IC01Responsibility allocate vessel.recovery to ic01.recoveryController {
        attribute :>> path = ImplementationPath::recovery;
        attribute :>> scope = "Plan, reassess and command recovery; does not itself produce thrust or retrieve the boat";
    }
    allocation recoveryActuation : IC01Responsibility allocate vessel.recoveryActuation to ic01.recoveryPropulsor {
        attribute :>> path = ImplementationPath::recovery;
        attribute :>> scope = "Execute permitted recovery commands; achieved upright/inverted thrust remains unverified";
    }
    allocation recordStorage : IC01Responsibility allocate vessel.recording to ic01.recordStorage {
        attribute :>> path = ImplementationPath::shared;
        attribute :>> scope = "Persist and expose records; supply and post-fault availability remain unresolved";
    }
    allocation primaryRecordPolicy : IC01Responsibility allocate vessel.recording to ic01.primaryController {
        attribute :>> path = ImplementationPath::primary;
        attribute :>> scope = "Generate and schedule primary records and readback";
    }
    allocation recoveryRecordPolicy : IC01Responsibility allocate vessel.recording to ic01.recoveryController {
        attribute :>> path = ImplementationPath::recovery;
        attribute :>> scope = "Generate and schedule recovery records; shared-storage survival is unverified";
    }
    allocation telemetry : IC01Responsibility allocate vessel.communications to ic01.telemetry {
        attribute :>> path = ImplementationPath::shared;
        attribute :>> scope = "Transmit records and report link availability; supply and interface arbitration remain unresolved";
    }
    allocation primaryCommunications : IC01Responsibility allocate vessel.communications to ic01.primaryController {
        attribute :>> path = ImplementationPath::primary;
        attribute :>> scope = "Queue and prioritize primary telemetry without blocking autonomy";
    }
    allocation recoveryCommunications : IC01Responsibility allocate vessel.communications to ic01.recoveryController {
        attribute :>> path = ImplementationPath::recovery;
        attribute :>> scope = "Queue and prioritize recovery telemetry; autonomy does not require a link";
    }
    allocation navigationToSupervisorPrimaryNavigationData : IC01Exchange allocate vessel.navigationToSupervisor to ic01.primaryNavigationData {
        attribute :>> path = ImplementationPath::primary;
        attribute :>> scope = "Candidate payload transfer; installed timing, transport and fault handling remain to be specified";
    }
    allocation navigationToSupervisorRecoveryNavigationData : IC01Exchange allocate vessel.navigationToSupervisor to ic01.recoveryNavigationData {
        attribute :>> path = ImplementationPath::recovery;
        attribute :>> scope = "Candidate payload transfer; installed timing, transport and fault handling remain to be specified";
    }
    allocation navigationToGuidancePrimaryNavigationData : IC01Exchange allocate vessel.navigationToGuidance to ic01.primaryNavigationData {
        attribute :>> path = ImplementationPath::primary;
        attribute :>> scope = "Candidate payload transfer; installed timing, transport and fault handling remain to be specified";
    }
    allocation windToGuidanceWindData : IC01Exchange allocate vessel.windToGuidance to ic01.windData {
        attribute :>> path = ImplementationPath::primary;
        attribute :>> scope = "Candidate payload transfer; installed timing, transport and fault handling remain to be specified";
    }
    allocation windToSupervisorWindData : IC01Exchange allocate vessel.windToSupervisor to ic01.windData {
        attribute :>> path = ImplementationPath::primary;
        attribute :>> scope = "Candidate payload transfer; installed timing, transport and fault handling remain to be specified";
    }
    allocation linkToSupervisorPrimaryLinkStatus : IC01Exchange allocate vessel.linkToSupervisor to ic01.primaryLinkStatus {
        attribute :>> path = ImplementationPath::primary;
        attribute :>> scope = "Candidate payload transfer; installed timing, transport and fault handling remain to be specified";
    }
    allocation linkToSupervisorRecoveryLinkStatus : IC01Exchange allocate vessel.linkToSupervisor to ic01.recoveryLinkStatus {
        attribute :>> path = ImplementationPath::recovery;
        attribute :>> scope = "Candidate payload transfer; installed timing, transport and fault handling remain to be specified";
    }
    allocation safetyToSupervisorRecoverySafetyToPrimary : IC01Exchange allocate vessel.safetyToSupervisor to ic01.recoverySafetyToPrimary {
        attribute :>> path = ImplementationPath::primary;
        attribute :>> scope = "Candidate payload transfer; installed timing, transport and fault handling remain to be specified";
    }
    allocation safetyToSupervisorPrimarySafetyToRecovery : IC01Exchange allocate vessel.safetyToSupervisor to ic01.primarySafetyToRecovery {
        attribute :>> path = ImplementationPath::recovery;
        attribute :>> scope = "Candidate payload transfer; installed timing, transport and fault handling remain to be specified";
    }
    allocation safetyToRecoveryPrimarySafetyToRecovery : IC01Exchange allocate vessel.safetyToRecovery to ic01.primarySafetyToRecovery {
        attribute :>> path = ImplementationPath::recovery;
        attribute :>> scope = "Candidate payload transfer; installed timing, transport and fault handling remain to be specified";
    }
    allocation tracksToCollisionPrimaryTrafficData : IC01Exchange allocate vessel.tracksToCollision to ic01.primaryTrafficData {
        attribute :>> path = ImplementationPath::primary;
        attribute :>> scope = "Candidate payload transfer; installed timing, transport and fault handling remain to be specified";
    }
    allocation tracksToCollisionRecoveryTrafficData : IC01Exchange allocate vessel.tracksToCollision to ic01.recoveryTrafficData {
        attribute :>> path = ImplementationPath::recovery;
        attribute :>> scope = "Candidate payload transfer; installed timing, transport and fault handling remain to be specified";
    }
    allocation navigationToCollisionPrimaryNavigationData : IC01Exchange allocate vessel.navigationToCollision to ic01.primaryNavigationData {
        attribute :>> path = ImplementationPath::primary;
        attribute :>> scope = "Candidate payload transfer; installed timing, transport and fault handling remain to be specified";
    }
    allocation navigationToCollisionRecoveryNavigationData : IC01Exchange allocate vessel.navigationToCollision to ic01.recoveryNavigationData {
        attribute :>> path = ImplementationPath::recovery;
        attribute :>> scope = "Candidate payload transfer; installed timing, transport and fault handling remain to be specified";
    }
    allocation navigationToBoundaryPrimaryNavigationData : IC01Exchange allocate vessel.navigationToBoundary to ic01.primaryNavigationData {
        attribute :>> path = ImplementationPath::primary;
        attribute :>> scope = "Candidate payload transfer; installed timing, transport and fault handling remain to be specified";
    }
    allocation navigationToBoundaryRecoveryNavigationData : IC01Exchange allocate vessel.navigationToBoundary to ic01.recoveryNavigationData {
        attribute :>> path = ImplementationPath::recovery;
        attribute :>> scope = "Candidate payload transfer; installed timing, transport and fault handling remain to be specified";
    }
    allocation permissionsToActuationSailingPermissions : IC01Exchange allocate vessel.permissionsToActuation to ic01.sailingPermissions {
        attribute :>> path = ImplementationPath::primary;
        attribute :>> scope = "Candidate payload transfer; installed timing, transport and fault handling remain to be specified";
    }
    allocation permissionsToRecoveryPrimaryPermissionsToRecovery : IC01Exchange allocate vessel.permissionsToRecovery to ic01.primaryPermissionsToRecovery {
        attribute :>> path = ImplementationPath::recovery;
        attribute :>> scope = "Candidate payload transfer; installed timing, transport and fault handling remain to be specified";
    }
    allocation sailingCommandsSailingCommandData : IC01Exchange allocate vessel.sailingCommands to ic01.sailingCommandData {
        attribute :>> path = ImplementationPath::primary;
        attribute :>> scope = "Candidate payload transfer; installed timing, transport and fault handling remain to be specified";
    }
    allocation supervisorRecordsPrimaryRecords : IC01Exchange allocate vessel.supervisorRecords to ic01.primaryRecords {
        attribute :>> path = ImplementationPath::primary;
        attribute :>> scope = "Candidate payload transfer; installed timing, transport and fault handling remain to be specified";
    }
    allocation supervisorRecordsRecoveryRecords : IC01Exchange allocate vessel.supervisorRecords to ic01.recoveryRecords {
        attribute :>> path = ImplementationPath::recovery;
        attribute :>> scope = "Candidate payload transfer; installed timing, transport and fault handling remain to be specified";
    }
    allocation supervisorTelemetryPrimaryTelemetry : IC01Exchange allocate vessel.supervisorTelemetry to ic01.primaryTelemetry {
        attribute :>> path = ImplementationPath::primary;
        attribute :>> scope = "Candidate payload transfer; installed timing, transport and fault handling remain to be specified";
    }
    allocation supervisorTelemetryRecoveryTelemetry : IC01Exchange allocate vessel.supervisorTelemetry to ic01.recoveryTelemetry {
        attribute :>> path = ImplementationPath::recovery;
        attribute :>> scope = "Candidate payload transfer; installed timing, transport and fault handling remain to be specified";
    }
    allocation navigationToRecoveryRecoveryNavigationData : IC01Exchange allocate vessel.navigationToRecovery to ic01.recoveryNavigationData {
        attribute :>> path = ImplementationPath::recovery;
        attribute :>> scope = "Candidate payload transfer; installed timing, transport and fault handling remain to be specified";
    }
    allocation tracksToRecoveryRecoveryTrafficData : IC01Exchange allocate vessel.tracksToRecovery to ic01.recoveryTrafficData {
        attribute :>> path = ImplementationPath::recovery;
        attribute :>> scope = "Candidate payload transfer; installed timing, transport and fault handling remain to be specified";
    }
    allocation recoveryCommandsRecoveryCommandData : IC01Exchange allocate vessel.recoveryCommands to ic01.recoveryCommandData {
        attribute :>> path = ImplementationPath::recovery;
        attribute :>> scope = "Candidate payload transfer; installed timing, transport and fault handling remain to be specified";
    }
    allocation recoveryRecordsRecoveryRecords : IC01Exchange allocate vessel.recoveryRecords to ic01.recoveryRecords {
        attribute :>> path = ImplementationPath::recovery;
        attribute :>> scope = "Candidate payload transfer; installed timing, transport and fault handling remain to be specified";
    }
    allocation recoveryTelemetryRecoveryTelemetry : IC01Exchange allocate vessel.recoveryTelemetry to ic01.recoveryTelemetry {
        attribute :>> path = ImplementationPath::recovery;
        attribute :>> scope = "Candidate payload transfer; installed timing, transport and fault handling remain to be specified";
    }
    allocation retainedRecordsToCommunicationsPrimaryRecordReadback : IC01Exchange allocate vessel.retainedRecordsToCommunications to ic01.primaryRecordReadback {
        attribute :>> path = ImplementationPath::primary;
        attribute :>> scope = "Candidate payload transfer; installed timing, transport and fault handling remain to be specified";
    }
    allocation retainedRecordsToCommunicationsRecoveryRecordReadback : IC01Exchange allocate vessel.retainedRecordsToCommunications to ic01.recoveryRecordReadback {
        attribute :>> path = ImplementationPath::recovery;
        attribute :>> scope = "Candidate payload transfer; installed timing, transport and fault handling remain to be specified";
    }
    allocation safetyToSupervisorPrimaryInternal : IC01InternalExchange allocate vessel.safetyToSupervisor to ic01.primaryController {
        attribute :>> path = ImplementationPath::primary;
        attribute :>> scope = "Internal interaction of coallocated responsibilities; software scheduling, validity propagation and fault handling remain unresolved";
    }
    allocation safetyToSupervisorRecoveryInternal : IC01InternalExchange allocate vessel.safetyToSupervisor to ic01.recoveryController {
        attribute :>> path = ImplementationPath::recovery;
        attribute :>> scope = "Internal interaction of coallocated responsibilities; software scheduling, validity propagation and fault handling remain unresolved";
    }
    allocation safetyToRecoveryRecoveryInternal : IC01InternalExchange allocate vessel.safetyToRecovery to ic01.recoveryController {
        attribute :>> path = ImplementationPath::recovery;
        attribute :>> scope = "Internal interaction of coallocated responsibilities; software scheduling, validity propagation and fault handling remain unresolved";
    }
    allocation reserveToSupervisorPrimaryInternal : IC01InternalExchange allocate vessel.reserveToSupervisor to ic01.primaryController {
        attribute :>> path = ImplementationPath::primary;
        attribute :>> scope = "Internal interaction of coallocated responsibilities; software scheduling, validity propagation and fault handling remain unresolved";
    }
    allocation reserveToSupervisorRecoveryInternal : IC01InternalExchange allocate vessel.reserveToSupervisor to ic01.recoveryController {
        attribute :>> path = ImplementationPath::recovery;
        attribute :>> scope = "Internal interaction of coallocated responsibilities; software scheduling, validity propagation and fault handling remain unresolved";
    }
    allocation reserveToRecoveryRecoveryInternal : IC01InternalExchange allocate vessel.reserveToRecovery to ic01.recoveryController {
        attribute :>> path = ImplementationPath::recovery;
        attribute :>> scope = "Internal interaction of coallocated responsibilities; software scheduling, validity propagation and fault handling remain unresolved";
    }
    allocation trafficToSupervisorPrimaryInternal : IC01InternalExchange allocate vessel.trafficToSupervisor to ic01.primaryController {
        attribute :>> path = ImplementationPath::primary;
        attribute :>> scope = "Internal interaction of coallocated responsibilities; software scheduling, validity propagation and fault handling remain unresolved";
    }
    allocation trafficToSupervisorRecoveryInternal : IC01InternalExchange allocate vessel.trafficToSupervisor to ic01.recoveryController {
        attribute :>> path = ImplementationPath::recovery;
        attribute :>> scope = "Internal interaction of coallocated responsibilities; software scheduling, validity propagation and fault handling remain unresolved";
    }
    allocation boundaryToSupervisorPrimaryInternal : IC01InternalExchange allocate vessel.boundaryToSupervisor to ic01.primaryController {
        attribute :>> path = ImplementationPath::primary;
        attribute :>> scope = "Internal interaction of coallocated responsibilities; software scheduling, validity propagation and fault handling remain unresolved";
    }
    allocation boundaryToSupervisorRecoveryInternal : IC01InternalExchange allocate vessel.boundaryToSupervisor to ic01.recoveryController {
        attribute :>> path = ImplementationPath::recovery;
        attribute :>> scope = "Internal interaction of coallocated responsibilities; software scheduling, validity propagation and fault handling remain unresolved";
    }
    allocation boundaryToGuidancePrimaryInternal : IC01InternalExchange allocate vessel.boundaryToGuidance to ic01.primaryController {
        attribute :>> path = ImplementationPath::primary;
        attribute :>> scope = "Internal interaction of coallocated responsibilities; software scheduling, validity propagation and fault handling remain unresolved";
    }
    allocation permissionsToGuidancePrimaryInternal : IC01InternalExchange allocate vessel.permissionsToGuidance to ic01.primaryController {
        attribute :>> path = ImplementationPath::primary;
        attribute :>> scope = "Internal interaction of coallocated responsibilities; software scheduling, validity propagation and fault handling remain unresolved";
    }
    allocation permissionsToRecoveryRecoveryInternal : IC01InternalExchange allocate vessel.permissionsToRecovery to ic01.recoveryController {
        attribute :>> path = ImplementationPath::recovery;
        attribute :>> scope = "Internal interaction of coallocated responsibilities; software scheduling, validity propagation and fault handling remain unresolved";
    }
    allocation boundaryToRecoveryRecoveryInternal : IC01InternalExchange allocate vessel.boundaryToRecovery to ic01.recoveryController {
        attribute :>> path = ImplementationPath::recovery;
        attribute :>> scope = "Internal interaction of coallocated responsibilities; software scheduling, validity propagation and fault handling remain unresolved";
    }
}

package BlueDog {
    doc /* Working architecture model, 2026-10-09.
     * Confirmed threshold: Bingen-Stevenson-Bingen round trip.
     * Repeated operation is a future endurance objective, outside current acceptance.
     * Qualifying round trips require no operator intervention; live monitoring is required.
     * Current design driver: one finite GorgeChallenge::transGorgeChallenge round trip.
     * Goals::hawaiiVoyage is a separate future mission with its own constraints.
     * Multi-day endurance with energy harvesting remains an earlier intent. SysML v2 learning is a project goal.
     * Decomposition identifies responsibilities; physical design remains open.
     * Tool checks are recorded in the modeling guide; design satisfaction links
     * are maintained separately and do not establish verification.
     */

    private import GorgeChallenge::*;
    private import OOSEM::*;

    package DesignIntent {
        doc /* Owner-imposed project constraints: one-person transport, construction on a
         * 250 mm cubic desktop printer, and serviceability between deployments. These
         * remain binding alongside the finite Gorge mission, not consequences of sailing success.
         */
    }

    package Goals {
        requirement def <'H-001'> HawaiiVoyage {
            metadata applicability : BlueDogMissionScope::Applicability { mission = BlueDogMissionScope::MissionKind::futureOcean; }
            metadata workStatus : ModelingMetadata::StatusInfo { status = ModelingMetadata::StatusKind::open; }
            doc /* The vessel shall complete an autonomous sailing voyage to Hawaii. */
            comment notes /* Gorge-specific challenge rules do not automatically apply to the ocean mission. */
            metadata rationale : ModelingMetadata::Rationale { text = "The Gorge is a proving ground for the ocean objective, not evidence of ocean readiness."; }
            metadata issue : ModelingMetadata::Issue { text = "Departure point, destination gate, route, duration, route/season suitability of the candidate ocean envelope, assistance/propulsion rules and acceptance evidence remain to be agreed."; }
        }
        requirement hawaiiVoyage : HawaiiVoyage;
    }

    package Mission {
        action def HawaiiMission {
            doc /* Mission decomposition supporting Goals::hawaiiVoyage.
             * This is not an executable sequence or a verified mission plan.
             * Route, landfall, endurance, and recovery criteria remain open.
             */
            action prepareAndLaunch;
            action sailOceanPassage;
            action approachDestination;
            action recoverBoatAndData;
            action manageEnergy;
            action monitorHealthAndRecover;
            action communicateWithOperator;
            action recordMissionData;
        }
        action def TransGorgeMission {
            doc /* Activity decomposition, not execution order.
             * TransGorgeCourse defines marker-referenced gates, subject to course release review.
             * The finite challenge has no completion deadline. GorgeChallenge defines
             * monitoring and recovery obligations; environmental allocations and
             * real recovery sites remain subject to review.
             * No operator intervention is permitted during a qualifying round trip.
             */
            action prepareAndLaunch;
            action sailOutbound;
            action turnAround;
            action sailHome;
            action recoverBoatAndData;
            action manageEnergy;
            action monitorHealthAndRecover;
            action communicateWithOperator;
            action recordMissionData;
        }
        action def SwellMonitoringMission {
            doc /* Stretch mission, not required for the initial round trip.
             * Station-keeping area, measurement products, and accuracy TBD.
             */
            action reachObservationArea;
            action maintainObservationArea;
            action measureAndRecordConditions;
            action returnForRecovery;
        }
    }

    package Architecture {
        doc /* System responsibility and external-context description. Boat is
         * not an installed assembly. BlueDogArchitectureCorrespondence maps its
         * responsibilities to LogicalVessel; IC01Candidate owns the provisional
         * equipment composition. HullAndRig remains a shared hardware concept. */
        #user part def Operator;
        part def MonitoringStation;
        #externalSystem part def ShoreSupport {
            part monitoringStation : MonitoringStation;
        }
        #environment part def Environment;
        #externalSystem part def OtherVessel {
            doc /* External traffic, including commercial ships, barges, fishing and recreational craft, with or without AIS. Behavior and cooperation are outside Blue Dog control. */
        }
        #hardware part def PrintedHull;
        #hardware part def SealedEnclosure;
        #hardware part def KeelAndBallast;
        #hardware part def HandlingInterfaces;
        part def RigConcept {
            doc /* Soft sail, tail-controlled rigid wing and directly rotated
             * fixed-camber wing retain equal development standing. No selected
             * rig or physical demonstration is implied by this responsibility. */
        }
        part def HullAndRig {
            part rig : RigConcept;
            part printedHull : PrintedHull;
            part enclosure : SealedEnclosure;
            part keelAndBallast : KeelAndBallast;
            part handling : HandlingInterfaces;
        }
        part def EnergyStorage;
        part def HarvestingInterface;
        part def PowerManagement;
        part def EnergySubsystem {
            part storage : EnergyStorage;
            part harvesting : HarvestingInterface;
            part powerManagement : PowerManagement;
        }
        part def PositionAndAttitude;
        part def WindSensing;
        part def TrafficSensing;
        part def NavigationAndSensing {
            part positionAndAttitude : PositionAndAttitude;
            part wind : WindSensing;
            part traffic : TrafficSensing;
        }
        part def MissionManager;
        part def CollisionAvoidance;
        part def BoundarySupervisor;
        part def GuidanceAndControl {
            part missionManager : MissionManager;
            part collisionAvoidance : CollisionAvoidance;
            part boundarySupervisor : BoundarySupervisor;
        }
        part def SailAndSteeringActuation;
        part def TelemetryRadio;
        part def AntennaSystem;
        part def CommandGateway;
        part def Communications {
            part telemetryRadio : TelemetryRadio;
            part antenna : AntennaSystem;
            part commandGateway : CommandGateway;
        }
        part def RecoveryPropulsion;
        part def RecoveryController;
        part def IngressMonitor;
        part def HealthAndRecovery {
            part motorSystem : RecoveryPropulsion;
            part recoveryController : RecoveryController;
            part ingressMonitor : IngressMonitor;
        }
        part def NavigationSignaling;
        part def DataRecording;
        part def ObservationPayload;

        #system part def Boat {
            doc /* System responsibility breakdown with identified hardware concepts.
             * Candidate architecture for the finite Gorge challenge. Future missions require separate allocation.
             * BlueDogLogicalArchitecture defines implementation-independent exchanges.
             * BlueDogPhysicalArchitecture describes a provisional IC-01 realization;
             * neither this responsibility tree nor that candidate establishes hardware qualification.
             */
            part hullAndRig : HullAndRig;
            part energy : EnergySubsystem;
            part navigation : NavigationAndSensing;
            part control : GuidanceAndControl;
            part actuation : SailAndSteeringActuation;
            part communications : Communications;
            part recovery : HealthAndRecovery;
            part recording : DataRecording;
            part signaling : NavigationSignaling;
            part observationPayload : ObservationPayload [0..1];
        }
        #systemContext part def MissionContext {
            part boat : Boat :>> systemOfInterest;
            part operator : Operator :>> users;
            part shoreSupport : ShoreSupport :> externalSystems;
            part :>> environment : Environment;
            part traffic : OtherVessel [0..*] :> externalSystems;
        }
        part missionContext : MissionContext;
    }

}

package BlueDogLogicalArchitecture {
    private import OOSEM::*;
    private import ScalarValues::*;
    doc /* Implementation-independent responsibilities and information exchanges.
     * Ports describe information contracts, not buses, processors or installed
     * equipment. Native scenario allocations identify who performs each action.
     * Candidate realization is separate in BlueDogPhysicalArchitecture. */

    #ioEntity item def NavigationEstimate {
        attribute coordinateReference : String;
        attribute headingReference : String;
        item context : BlueDogInterfaceContracts::ObservationContext;
        attribute valid : Boolean;
        attribute observedAt : ISQ::TimeValue;
        attribute latitude : ISQ::AngularMeasureValue;
        attribute longitude : ISQ::AngularMeasureValue;
        attribute heading : ISQ::AngularMeasureValue;
    }
    #ioEntity item def SafetyObservation {
        attribute valid : ScalarValues::Boolean;
        item context : BlueDogInterfaceContracts::ObservationContext;
        attribute capsized : Boolean;
        attribute uprightControlRestored : Boolean;
        attribute requiredSafetyConfirmed : Boolean;
        attribute observedAt : ISQ::TimeValue;
        doc /* Confirmation covers currently required navigation, collision
         * assessment, boundary awareness, energy and recovery capabilities.
         * A primary failure is distinct from loss of the required capability.
         * Confirmation while inverted or using backup equipment requires explicit
         * evidence; absence of that observation cannot establish safe continuation. */
    }
    #ioEntity item def ReserveAssessment {
        attribute observedAt : ISQ::TimeValue;
        item context : BlueDogInterfaceContracts::ObservationContext;
        attribute usableEnergy : ISQ::EnergyValue;
        attribute protectedReserve : ISQ::EnergyValue;
        attribute threatened : Boolean;
        attribute valid : Boolean;
    }
    #ioEntity item def TrafficAssessment {
        item context : BlueDogInterfaceContracts::ObservationContext;
        attribute conflict : Boolean;
        attribute valid : Boolean;
        attribute observedAt : ISQ::TimeValue;
    }
    #ioEntity item def BoundaryAssessment {
        attribute observedAt : ISQ::TimeValue;
        item context : BlueDogInterfaceContracts::ObservationContext;
        attribute insidePermittedArea : Boolean;
        attribute avoidanceRequired : Boolean;
        attribute valid : Boolean;
        doc /* Evaluated against the configured water domain, exclusions and
         * current navigation observation; this is not a surveyed-site approval. */
    }
    #ioEntity item def TrafficTrack {
        attribute bearingReference : String;
        attribute rangeReference : String;
        attribute headingReference : String;
        item context : BlueDogInterfaceContracts::ObservationContext;
        attribute identity : String;
        attribute observedAt : ISQ::TimeValue;
        attribute bearing : ISQ::AngularMeasureValue;
        attribute range : ISQ::LengthValue;
        attribute speed : ISQ::SpeedValue;
        attribute heading : ISQ::AngularMeasureValue;
        attribute valid : Boolean;
        doc /* A tracked contact may come from AIS or non-cooperative sensing.
         * Declared observation validity does not establish detection coverage. */
    }
    #ioEntity item def TrafficObservation {
        attribute valid : ScalarValues::Boolean;
        attribute observedAt : ISQ::TimeValue;
        item context : BlueDogInterfaceContracts::ObservationContext;
        item tracks : TrafficTrack [0..*];
        attribute coverageConfirmed : Boolean;
    }
    #ioEntity item def OperationPermission {
        item context : BlueDogInterfaceContracts::CommandContext;
        attribute sailingPermitted : Boolean;
        attribute gateScoringPermitted : Boolean;
        attribute harvestPermitted : Boolean;
        attribute abortLatched : Boolean;
        attribute qualificationLost : Boolean;
    }
    #ioEntity item def RecoveryCommand {
        item context : BlueDogInterfaceContracts::CommandContext;
        attribute recoveryRequested : Boolean;
        attribute propulsionPermitted : Boolean;
        doc /* Powered recovery follows qualification loss. This command does
         * not assert shore reachability or available independent hardware. */
    }
    #ioEntity item def MissionRecord {
        item context : BlueDogInterfaceContracts::ObservationContext;
        attribute eventKind : String;
        attribute observedAt : ISQ::TimeValue;
        attribute qualificationLost : Boolean;
        attribute abortLatched : Boolean;
    }
    port def NavigationOutput { out item estimate : NavigationEstimate; }
    port def NavigationInput { in item estimate : NavigationEstimate; }
    port def WindOutput { out item estimate : BlueDogMethod::WindEstimate; }
    port def WindInput { in item estimate : BlueDogMethod::WindEstimate; }
    port def LinkOutput { out item observation : BlueDogMethod::LinkObservation; }
    port def LinkInput { in item observation : BlueDogMethod::LinkObservation; }
    port def SafetyOutput { out item observation : SafetyObservation; }
    port def SafetyInput { in item observation : SafetyObservation; }
    port def ReserveOutput { out item assessment : ReserveAssessment; }
    port def ReserveInput { in item assessment : ReserveAssessment; }
    port def TrafficOutput { out item assessment : TrafficAssessment; }
    port def TrafficInput { in item assessment : TrafficAssessment; }
    port def BoundaryOutput { out item assessment : BoundaryAssessment; }
    port def BoundaryInput { in item assessment : BoundaryAssessment; }
    port def TracksOutput { out item observation : TrafficObservation; }
    port def TracksInput { in item observation : TrafficObservation; }
    port def PermissionOutput { out item permission : OperationPermission; }
    port def PermissionInput { in item permission : OperationPermission; }
    port def CommandOutput { out item command : BlueDogMethod::SailingCommand; }
    port def CommandInput { in item command : BlueDogMethod::SailingCommand; }
    port def RecordOutput { out item record : MissionRecord; }
    port def RecordInput { in item record : MissionRecord; }
    port def RecoveryOutput { out item command : RecoveryCommand; }
    port def RecoveryInput { in item command : RecoveryCommand; }

    #logical part def NavigationEstimation { port navigation : NavigationOutput; }
    #logical part def WindEstimation { port wind : WindOutput; }
    #logical part def SafetyAssessment { port safety : SafetyOutput; }
    #logical part def EnergyManagement { port reserve : ReserveOutput; }
    #logical part def TrafficObservationService { port tracks : TracksOutput; }
    #logical part def CollisionAssessment {
        port tracks : TracksInput;
        port navigation : NavigationInput;
        port traffic : TrafficOutput;
    }
    #logical part def BoundaryManagement {
        port navigation : NavigationInput;
        port boundary : BoundaryOutput;
    }
    #logical part def MissionSupervision {
        port navigation : NavigationInput;
        port wind : WindInput;
        port link : LinkInput;
        port safety : SafetyInput;
        port reserve : ReserveInput;
        port traffic : TrafficInput;
        port boundary : BoundaryInput;
        port permissions : PermissionOutput;
        port events : RecordOutput;
    }
    #logical part def Guidance {
        port navigation : NavigationInput;
        port wind : WindInput;
        port boundary : BoundaryInput;
        port permissions : PermissionInput;
        port commands : CommandOutput;
    }
    #logical part def SailingActuation {
        port commands : CommandInput;
        port permissions : PermissionInput;
    }
    #logical part def RecoveryManagement {
        doc /* Select and reassess a reachable shore plan and command recovery.
         * Navigation, traffic, boundary and reserve assessments are explicit
         * inputs. Thrust execution belongs to RecoveryActuation; shore capture
         * and operator pickup remain separate physical/procedural obligations. */
        port navigation : NavigationInput;
        port tracks : TracksInput;
        port boundary : BoundaryInput;
        port events : RecordOutput;
        port safety : SafetyInput;
        port reserve : ReserveInput;
        port permissions : PermissionInput;
        port commands : RecoveryOutput;
    }
    #logical part def RecoveryActuation {
        port commands : RecoveryInput;
        doc /* Execute permitted recovery propulsion. A command is not evidence
         * of achieved thrust, inverted operation, shore arrival or retention. */
    }
    #logical part def Recording {
        port events : RecordInput;
        port retained : RecordOutput;
    }
    #logical part def Communications {
        port events : RecordInput;
        port retained : RecordInput;
        port status : LinkOutput;
    }
    part def LogicalVessel {
        part navigation : NavigationEstimation;
        part wind : WindEstimation;
        part safety : SafetyAssessment;
        part energy : EnergyManagement;
        part collision : CollisionAssessment;
        part boundary : BoundaryManagement;
        part trafficObservation : TrafficObservationService;
        part supervision : MissionSupervision;
        part guidance : Guidance;
        part actuation : SailingActuation;
        part recovery : RecoveryManagement;
        part recoveryActuation : RecoveryActuation;
        part recording : Recording;
        part communications : Communications;
        flow navigationToSupervisor from navigation.navigation.estimate to supervision.navigation.estimate;
        flow navigationToGuidance from navigation.navigation.estimate to guidance.navigation.estimate;
        flow windToGuidance from wind.wind.estimate to guidance.wind.estimate;
        flow windToSupervisor from wind.wind.estimate to supervision.wind.estimate;
        flow linkToSupervisor from communications.status.observation to supervision.link.observation;
        flow safetyToSupervisor from safety.safety.observation to supervision.safety.observation;
        flow safetyToRecovery from safety.safety.observation to recovery.safety.observation;
        flow reserveToSupervisor from energy.reserve.assessment to supervision.reserve.assessment;
        flow reserveToRecovery from energy.reserve.assessment to recovery.reserve.assessment;
        flow trafficToSupervisor from collision.traffic.assessment to supervision.traffic.assessment;
        flow tracksToCollision from trafficObservation.tracks.observation to collision.tracks.observation;
        flow navigationToCollision from navigation.navigation.estimate to collision.navigation.estimate;
        flow navigationToBoundary from navigation.navigation.estimate to boundary.navigation.estimate;
        flow boundaryToSupervisor from boundary.boundary.assessment to supervision.boundary.assessment;
        flow boundaryToGuidance from boundary.boundary.assessment to guidance.boundary.assessment;
        flow permissionsToGuidance from supervision.permissions.permission to guidance.permissions.permission;
        flow permissionsToActuation from supervision.permissions.permission to actuation.permissions.permission;
        flow permissionsToRecovery from supervision.permissions.permission to recovery.permissions.permission;
        flow sailingCommands from guidance.commands.command to actuation.commands.command;
        flow supervisorRecords from supervision.events.record to recording.events.record;
        flow supervisorTelemetry from supervision.events.record to communications.events.record;
        flow navigationToRecovery from navigation.navigation.estimate to recovery.navigation.estimate;
        flow tracksToRecovery from trafficObservation.tracks.observation to recovery.tracks.observation;
        flow boundaryToRecovery from boundary.boundary.assessment to recovery.boundary.assessment;
        flow recoveryCommands from recovery.commands.command to recoveryActuation.commands.command;
        flow recoveryRecords from recovery.events.record to recording.events.record;
        flow recoveryTelemetry from recovery.events.record to communications.events.record;
        flow retainedRecordsToCommunications from recording.retained.record to communications.retained.record;
    }
    part vessel : LogicalVessel;
}

package BlueDogPhysicalArchitecture {
    private import OOSEM::*;
    private import ScalarValues::*;
    private import BlueDogLogicalArchitecture::*;
    doc /* Provisional physical realization of IC-01's mass/energy and recovery
     * hypothesis. Separate parts make intended fault containment inspectable;
     * they do not demonstrate electrical, software or environmental independence.
     * Catalog equipment, processor partition and installed sensing remain open.
     * Ports and flows identify candidate interfaces without specifying connector,
     * bus, voltage, current, throughput or proven inverted performance. */
    #ioEntity item def ElectricalSupply {
        attribute availablePower : ISQ::PowerValue;
        attribute available : Boolean;
    }
    #ioEntity item def MonitoredBankState {
        item context : BlueDogInterfaceContracts::ObservationContext;
        attribute usableEnergy : ISQ::EnergyValue;
        attribute valid : Boolean;
        attribute observedAt : ISQ::TimeValue;
        doc /* Battery observation used with a route-dependent recovery demand;
         * nameplate capacity alone does not establish usable energy or reserve. */
    }
    port def SupplyOutput { out item electrical : ElectricalSupply; }
    port def SupplyInput { in item electrical : ElectricalSupply; }
    port def BankStateOutput { out item observation : MonitoredBankState; }
    port def BankStateInput { in item observation : MonitoredBankState; }
    #hardware part def Battery {
        attribute nameplateWh : Real;
        port output : SupplyOutput;
        port monitor : BankStateOutput;
        doc /* The monitor is a candidate required interface; its sensing,
         * estimation and installation have not been selected or calibrated. */
    }
    #hardware part def NavigationSensors {
        port power : SupplyInput;
        port navigation : NavigationOutput;
    }
    #hardware part def WindSensor {
        ref part installation : BlueDogWindEquipment::Installation = BlueDogWindEquipment::challenge;
        port power : SupplyInput;
        port wind : WindOutput;
    }
    #hardware part def ObservationEquipment {
        port power : SupplyInput;
        port tracks : TracksOutput;
    }
    #hardware part def Controller {
        port power : SupplyInput;
        port link : LinkInput;
        port navigation : NavigationInput;
        port wind : WindInput;
        port tracks : TracksInput;
        port safety : SafetyInput;
        port assessedSafety : SafetyOutput;
        port mainBank : BankStateInput;
        port recoveryBank : BankStateInput;
        port commands : CommandOutput;
        port recovery : RecoveryOutput;
        port permissions : PermissionOutput;
        port peerPermissions : PermissionInput;
        port retained : RecordInput;
        port events : RecordOutput;
        doc /* SafetyAssessment is allocated here; its output aggregates current
         * sensing, actuation, energy and health evidence, not navigation alone.
         * The implementation, peer-timeout policy and independent failure detection
         * are unresolved. Receiving a peer report does not prove its truth. */
    }
    #hardware part def SailingActuators {
        port power : SupplyInput;
        port commands : CommandInput;
        port permissions : PermissionInput;
    }
    #hardware part def RecoveryPropulsor {
        port power : SupplyInput;
        port recovery : RecoveryInput;
    }
    #hardware part def RecordStorage {
        port power : SupplyInput;
        port events : RecordInput;
        port retained : RecordOutput;
        doc /* Readback supports queued telemetry. Retention, arbitration and
         * availability after a primary fault require an installed interface and
         * supply decision; this interface does not establish survivability. */
    }
    #hardware part def TelemetryEquipment {
        port power : SupplyInput;
        port events : RecordInput;
        port status : LinkOutput;
    }
    #hardware part def IC01Candidate {
        metadata workStatus : ModelingMetadata::StatusInfo { status = ModelingMetadata::StatusKind::open; }
        metadata issue : ModelingMetadata::Issue {
            text = "Independent recovery power, navigation, observation, control and thrust are unverified hypotheses. Establish common-cause isolation, inverted sensing/propulsion, sealing, load and interface evidence before hardware acceptance. Telemetry and record-storage bus assignment remains unresolved; the 8 W recovery essential-load allowance is not an installed load measurement or proof that those functions survive on the 60 Wh bank.";
        }
        part mainBattery : Battery { attribute :>> nameplateWh = BlueDogIC01::design.battery_Wh; }
        part recoveryBattery : Battery { attribute :>> nameplateWh = BlueDogIC01::integration.recoveryBatteryWh; }
        part primaryNavigation : NavigationSensors;
        part windSensor : WindSensor;
        part primaryObservation : ObservationEquipment;
        part primaryController : Controller;
        part sailingActuators : SailingActuators;
        part recoveryNavigation : NavigationSensors;
        part recoveryObservation : ObservationEquipment;
        part recoveryController : Controller;
        part recoveryPropulsor : RecoveryPropulsor;
        part recordStorage : RecordStorage;
        part telemetry : TelemetryEquipment;
        part hullAndRig : BlueDog::Architecture::HullAndRig;
        flow mainNavigationPower from mainBattery.output.electrical to primaryNavigation.power.electrical;
        flow windPower from mainBattery.output.electrical to windSensor.power.electrical;
        flow mainObservationPower from mainBattery.output.electrical to primaryObservation.power.electrical;
        flow mainControllerPower from mainBattery.output.electrical to primaryController.power.electrical;
        flow sailingPower from mainBattery.output.electrical to sailingActuators.power.electrical;
        flow recoveryNavigationPower from recoveryBattery.output.electrical to recoveryNavigation.power.electrical;
        flow recoveryObservationPower from recoveryBattery.output.electrical to recoveryObservation.power.electrical;
        flow recoveryControllerPower from recoveryBattery.output.electrical to recoveryController.power.electrical;
        flow recoveryPropulsionPower from recoveryBattery.output.electrical to recoveryPropulsor.power.electrical;
        flow mainBankToPrimary from mainBattery.monitor.observation to primaryController.mainBank.observation;
        flow recoveryBankToPrimary from recoveryBattery.monitor.observation to primaryController.recoveryBank.observation;
        flow recoveryBankToRecovery from recoveryBattery.monitor.observation to recoveryController.recoveryBank.observation;
        flow mainBankToRecovery from mainBattery.monitor.observation to recoveryController.mainBank.observation;
        flow primaryNavigationData from primaryNavigation.navigation.estimate to primaryController.navigation.estimate;
        flow windData from windSensor.wind.estimate to primaryController.wind.estimate;
        flow primaryTrafficData from primaryObservation.tracks.observation to primaryController.tracks.observation;
        flow primarySafetyToRecovery from primaryController.assessedSafety.observation to recoveryController.safety.observation;
        flow recoverySafetyToPrimary from recoveryController.assessedSafety.observation to primaryController.safety.observation;
        flow sailingPermissions from primaryController.permissions.permission to sailingActuators.permissions.permission;
        flow primaryPermissionsToRecovery from primaryController.permissions.permission to recoveryController.peerPermissions.permission;
        flow recoveryPermissionsToPrimary from recoveryController.permissions.permission to primaryController.peerPermissions.permission;
        flow sailingCommandData from primaryController.commands.command to sailingActuators.commands.command;
        flow recoveryNavigationData from recoveryNavigation.navigation.estimate to recoveryController.navigation.estimate;
        flow recoveryTrafficData from recoveryObservation.tracks.observation to recoveryController.tracks.observation;
        flow recoveryCommandData from recoveryController.recovery.command to recoveryPropulsor.recovery.command;
        flow primaryRecords from primaryController.events.record to recordStorage.events.record;
        flow recoveryRecords from recoveryController.events.record to recordStorage.events.record;
        flow primaryTelemetry from primaryController.events.record to telemetry.events.record;
        flow recoveryTelemetry from recoveryController.events.record to telemetry.events.record;
        flow primaryLinkStatus from telemetry.status.observation to primaryController.link.observation;
        flow recoveryLinkStatus from telemetry.status.observation to recoveryController.link.observation;
        flow primaryRecordReadback from recordStorage.retained.record to primaryController.retained.record;
        flow recoveryRecordReadback from recordStorage.retained.record to recoveryController.retained.record;
    }
    part ic01 : IC01Candidate {
        ref part configuration : MarineDesign::Design = BlueDogIC01::design;
        ref part integration = BlueDogIC01::integration;
        doc /* Candidate assembly for this named geometry and capability hypothesis.
         * Configuration references do not qualify installed hardware. */
    }
}

package BlueDogBehaviorContracts {
    private import ScalarValues::*;
    private import ISQ::*;
    private import ModelingMetadata::refinement;
    doc /* Partial executable consumer contracts for the current Gorge mission.
     * NASA SE Handbook 4.3.1.2.2 and defense SE Guidebook 2026 section 6.2.3
     * inform end-to-end functions/allocation; SysML 2.0 sections 7.17-7.18
     * govern action semantics. Actual outcomes follow the named requirements.
     * No hardware scheduler, synchronized clock or durable storage is inferred. */

    action def AssessObservationUsability {
        in producerValid : Boolean [1];
        in contextApplicable : Boolean [1];
        in clockEstablished : Boolean [1];
        in observedAt : TimeValue [1];
        in now : TimeValue [1];
        in maximumAge : TimeValue [1];
        out usable : Boolean [1];
        first start;
        then action assess {
            assign usable := BlueDogInterfaceContracts::ObservationUsable(
                producerValid,contextApplicable,clockEstablished,observedAt,now,maximumAge);
        }
        then done;
    }
    action def SailingActuationGate {
        doc /* Evaluate immediately before dispatch against current observations
         * and permission, not only at command creation. Boolean applicability
         * inputs are assessed using the interface contracts; they are not defaults. */
        in commandApplicable : Boolean [1];
        in permissionApplicable : Boolean [1];
        in sailingPermitted : Boolean [1];
        in abortLatched : Boolean [1];
        in qualificationLost : Boolean [1];
        in capsized : Boolean [1];
        in windUsable : Boolean [1];
        in navigationUsable : Boolean [1];
        in requiredSafetyConfirmed : Boolean [1];
        out actuate : Boolean [1];
        first start;
        then action gate {
            assign actuate := commandApplicable and permissionApplicable and sailingPermitted
            and not abortLatched and not qualificationLost and not capsized
            and windUsable and navigationUsable and requiredSafetyConfirmed;
        }
        then done;
    }
    action def RecoveryActuationGate {
        doc /* R-101 inhibits motor thrust while qualifying or status unknown.
         * E-138 requires durable disqualification before commanded motor enable.
         * R-102 requires established recovery authorization after restart.
         * Abort is intentionally not a motor inhibit: recovery follows abort. */
        in recoveryRequested : Boolean [1];
        in commandApplicable : Boolean [1];
        in recoveryAuthorized : Boolean [1];
        in qualificationStateKnown : Boolean [1];
        in qualifying : Boolean [1];
        in disqualificationStored : Boolean [1];
        in recoveryPathAvailable : Boolean [1];
        in inhibitActive : Boolean [1];
        out motorEnable : Boolean [1];
        first start;
        then action gate {
            assign motorEnable := recoveryRequested and commandApplicable and recoveryAuthorized
            and qualificationStateKnown and not qualifying and disqualificationStored
            and recoveryPathAvailable and not inhibitActive;
        }
        then done;
    }
    action def RestoreQualification {
        doc /* Explicit restart assessment, distinct from constructing a new
         * attempt. E-139/E-145 require nonqualifying fallback for missing or
         * inconsistent persisted state. A live disqualification cannot be erased
         * by restoring an older record. Persistence and the 30 s restoration
         * deadline still need an actual storage/restart implementation. */
        in recordValid : Boolean [1];
        in persistedQualificationLost : Boolean [1];
        in currentQualificationLost : Boolean [1];
        out qualificationLostNext : Boolean [1];
        first start;
        then action restore {
            assign qualificationLostNext := currentQualificationLost or not recordValid or persistedQualificationLost;
        }
        then done;
    }
    action navigationValidation : AssessObservationUsability;
    action sailingGate : SailingActuationGate;
    action recoveryGate : RecoveryActuationGate;
    action restartQualification : RestoreQualification;
    allocate navigationValidation to BlueDogLogicalArchitecture::vessel.navigation;
    allocate sailingGate to BlueDogLogicalArchitecture::vessel.actuation;
    allocate recoveryGate to BlueDogLogicalArchitecture::vessel.recoveryActuation;
    allocate restartQualification to BlueDogLogicalArchitecture::vessel.supervision;
    #refinement dependency navigationAssessment from AssessObservationUsability to BlueDogMethod::Scenarios::ValidateNavigation;
    #refinement dependency sailingAssessment from SailingActuationGate to BlueDogMethod::Scenarios::ApplySailingCommand;
    #refinement dependency recoveryAssessment from RecoveryActuationGate to BlueDogMethod::Scenarios::ApplyRecoveryCommand;
    dependency motorInvariant from RecoveryActuationGate to BlueDogRequirements::motorQualificationInvariant;
    dependency durableAuthorization from RecoveryActuationGate to BlueDogRequirements::qualificationPersistence;
    dependency freshAuthorization from RecoveryActuationGate to BlueDogRequirements::freshRecoveryCommand;
    dependency restorationPolicy from RestoreQualification to BlueDogRequirements::qualificationRestoration;
    dependency unknownFallback from RestoreQualification to BlueDogRequirements::unknownQualificationFallback;
    metadata issue : ModelingMetadata::Issue {
        text = "B-01: Bind installed message contexts to usability, current permissions and consumer gates; scalar conceptual simulations do not implement serialization. B-02: Demonstrate atomic durable state, acknowledgment ordering, all restriction restoration and restart deadlines on selected hardware. B-03: Resolve controller concurrency, command arbitration, resource ownership and timeout budgets, including abort during capsize/recovery. B-04: Implement and measure estimators, achieved actuation and repeated dynamic recovery; descriptive scenarios do not prove these functions.";
    }
}

package BlueDogDesignDecisions {
    private import ScalarValues::*;
    part def Decision {
        attribute disposition : String;
        attribute evidenceNeeded : String;
    }
    part sizingBaseline : Decision {
        attribute :>> disposition = "Use the fixed-camber rotating-mast wing as the first numerical sizing baseline; no final sail downselect.";
        attribute :>> evidenceNeeded = "Comparable both-tack polars, wet-cycle durability, actuator energy, mass/CG and dynamic recovery evidence for the alternatives.";
        metadata rationale : ModelingMetadata::Rationale {
            text = "The existing manufacturing CAD supplies a measured section and a practical starting geometry. This enables coupled sizing while preserving the tail-controlled wing and soft sail as equal development contenders for the finite Gorge mission. Availability of CAD is not proof of superior sailing performance.";
        }
        metadata issue : ModelingMetadata::Issue { text = "The source CAD is a manufacturing prototype, not the challenge vessel; the rectangular VSP wing uses its complete midspan section rather than reproducing its swept planform."; }
    }
    dependency baselineCandidate from sizingBaseline to BlueDogSailTrade::camberedWing;
    dependency retainedAlternative from sizingBaseline to BlueDogSailTrade::tailWing;
    dependency softSailAlternative from sizingBaseline to BlueDogSailTrade::softSail;
    dependency baselinePurpose from sizingBaseline to BlueDogRequirements::cruiseEvidence;

    part holdingDrive : Decision {
        attribute :>> disposition = "Evaluate non-backdrivable gearing as an option, not a selected or qualified component.";
        attribute :>> evidenceNeeded = "Motor-off holding under shock, wear, temperature and lubrication changes; moving efficiency, controller demand, jam and power-loss recovery tests.";
        metadata rationale : ModelingMetadata::Rationale { text = "Zero motor holding current can reduce finite mission energy consumption, but gear friction and trim movement still consume energy. A locked gearbox retains the last mast angle and requires explicit storm and capsize assessment."; }
    }
    dependency holdingEnergy from holdingDrive to BlueDogRequirements::multiDayEndurance;
    dependency holdingRecovery from holdingDrive to BlueDogRequirements::capsizeControlRecovery;
    dependency holdingCalculation from holdingDrive to MarineActuation::DrivePower;

    part aerodynamicScope : Decision {
        attribute :>> disposition = "Use restricted attached-flow VSPAERO sensitivity evidence with conservative sizing assumptions and separate actuator-moment uncertainty; no measured polar is available for this CAD.";
        attribute :>> evidenceNeeded = "Low-Reynolds-number viscous drag, stall, broadside response, thickness sensitivity and both-tack moment measurements; converged heel/wind/trim response across the sizing grid.";
        metadata rationale : ModelingMetadata::Rationale { text = "Potential-flow interpolation is suitable for a provisional force-balance model. Mesh convergence and direct candidate checks establish numerical consistency only. Rounded section ends and assumed wake attachment require physical validation; square-sail/downwind performance is not established by VLM."; }
    }
    dependency heelSensitivityEvidence from aerodynamicScope to BlueDogWingHeel::sweepInputs;
    dependency sizingAerodynamicPolicy from aerodynamicScope to BlueDogAerodynamicPolicy::sizing;
    dependency polarPurpose from aerodynamicScope to BlueDogRequirements::cruiseEvidence;
    dependency polarCalculation from aerodynamicScope to MarineSailing::Evaluate;

    part structuralScope : Decision {
        attribute :>> disposition = "Credit finite glass/epoxy laminate sections for bending; give printed substrate no bending-strength credit.";
        attribute :>> evidenceNeeded = "Wet/jointed coupon strength and stiffness, glass-to-print bonds, ribs, attachments, fatigue, buckling and impact tests.";
        metadata rationale : ModelingMetadata::Rationale { text = "Thin-wall inertia exceeded the solid-section bound in an earlier sizing trial. Polygon offsets now define finite-thickness section properties. Printed walls/ribs, seams and finish still contribute mass; preliminary material targets are not measured properties."; }
    }
    dependency structureChoice from structuralScope to BlueDogStructure::hybridConstruction;
    dependency structureCriteria from structuralScope to BlueDogStructure::structuralIntegrity;
    dependency structureCalculation from structuralScope to MarineStructures::DesignMargins;

    part recoveryScope : Decision {
        attribute :>> disposition = "Treat static full-roll restoring curves as screening evidence, separate from dynamic self-righting.";
        attribute :>> evidenceNeeded = "Dynamic releases, pitch stability, ingress/drainage, control restoration and credible failure-state geometry.";
        metadata rationale : ModelingMetadata::Rationale { text = "Positive sampled roll moments on a pitch-unstable equilibrium branch do not establish a recovery trajectory. Freely flooded material and fully retained water are distinct static sensitivities, not leakage or slosh predictions."; }
    }
    dependency recoveryCriteria from recoveryScope to BlueDogRequirements::selfRighting;
    dependency recoveryCalculation from recoveryScope to MarineHydrostatics::Balance;

    part energyEvidenceAcceptance : Decision {
        attribute :>> disposition = "Set evidenceAccepted only after review of evidence for the same installed configuration.";
        attribute :>> evidenceNeeded = "Non-overlapping installed-load coverage; measured power and duty bounds that preserve required functions; installed harvester route/season bounds including outages; temperature/end-of-service battery limits; conservative initial energy; consistent stored-energy and bus boundaries; interval resolution, uncertainty, repeat-cycle phase, source identifiers, configuration revision and review disposition.";
        metadata rationale : ModelingMetadata::Rationale { text = "A review Boolean does not automatically audit the records. Recovery demand is a battery withdrawal rate and its reserve stays inside usable capacity. Saving power by violating navigation, collision assessment, signaling, logging or communications does not establish sustained operation. A finite synthetic campaign cannot establish indefinite service."; }
    }
    dependency energyAcceptance from energyEvidenceAcceptance to BlueDogRequirements::energyEvidenceReadiness;
    dependency energyVerification from energyEvidenceAcceptance to BlueDogEnergy::SustainedEnergyVerification;

    part uncertaintyPolicy : Decision {
        attribute :>> disposition = "Separate nominal feasibility, adverse engineering sensitivities and physical qualification.";
        attribute :>> evidenceNeeded = "Measured uncertainty bounds and environmental exposure; hardware packaging/CG; robust feasibility with sufficient mission margins.";
        metadata rationale : ModelingMetadata::Rationale { text = "The size search is local and its variable brackets are numerical or model-domain limits. Mesh reserves are numerical allowances, not engineering safety factors. Sensitivity cases are not probabilities. Failed local operating solves do not prove physical impossibility or global infeasibility."; }
    }
    dependency uncertaintyCases from uncertaintyPolicy to BlueDogCoupledUncertainty::Inputs;
    dependency missionEvidence from uncertaintyPolicy to BlueDogRequirements::missionEvidence;
    part trafficCourtesy : Decision {
        attribute disposition :>> disposition = "Prefer safe, rule-consistent routes, operating windows and trajectories that reduce the likelihood of crewed vessels needing to maneuver. Accept delay or reduced mission progress to avoid developing encounters. Once encounter duties apply, preserve required predictable behavior and act when permitted or necessary; this is not an always-yield policy.";
        attribute evidenceNeeded :>> evidenceNeeded = "Compare alternatives against the same traffic scenarios using close-encounter exposure, predicted need for other-vessel action and mission delay, with explicit behavior and sensing assumptions. These are comparative design measures, not evidence of why another skipper acted or challenge pass/fail criteria. The preference is not yet implemented as a planner objective or validated by the existing replay.";
    }
    dependency courtesyWithinNavigationDuties from trafficCourtesy to GorgeChallenge::navigationRules;
    dependency courtesyCollisionSafety from trafficCourtesy to GorgeChallenge::trafficCoexistence;
}

package BlueDogInterfaceContracts {
    private import ScalarValues::*;
    private import ISQ::*;
    private import SI::*;
    doc /* Candidate logical data contracts. Source basis: NASA SE Handbook
     * 6.3.1.2.2-3; historical NASA SWE-112 section 3 (DI-IPSC-81436A-based
     * guidance); OMG SysML 2.0 sections 7.12-7.16. These definitions do not
     * select transport, serialize messages or implement runtime acceptance. */

    item def ObservationContext {
        attribute sourceIdentity : String;
        attribute configurationIdentity : String;
        attribute clockIdentity : String;
        attribute sourceEpoch : String;
        attribute sequence : Integer;
        doc /* Identity and sequence are semantic provenance, not authentication.
         * Epoch changes on producer restart; ordering is meaningful only within
         * the identified source/epoch. Clock identity requires an established
         * epoch, synchronization and uncertainty contract before comparing times. */
    }
    item def CommandContext {
        attribute authorityIdentity : String;
        attribute configurationIdentity : String;
        attribute clockIdentity : String;
        attribute authorityEpoch : String;
        attribute sequence : Integer;
        attribute issuedAt : TimeValue;
        attribute validUntil : TimeValue;
        doc /* Times use one identified monotonic reference. Consumers must use
         * an agreed authority epoch and ordering rule. Expiry cannot grant
         * permission or clear an abort. Arbitration, restart and inhibit design
         * remain unresolved; these fields do not establish an independent path. */
    }
    calc def ObservationUsable {
        doc /* Parameterized consumer precondition, not a selected freshness
         * policy. All comparisons require one established clock and applicable
         * configuration/frame. Producer validity alone is insufficient. A
         * negative observation may be valid. Bounds here are inclusive; a
         * consumer's allocated criterion must justify its maximumAge. */
        in producerValid : Boolean;
        in contextApplicable : Boolean;
        in clockEstablished : Boolean;
        in observedAt : TimeValue;
        in now : TimeValue;
        in maximumAge : TimeValue;
        return usable : Boolean = producerValid and contextApplicable and clockEstablished
        and maximumAge >= 0 [s] and observedAt <= now and now - observedAt <= maximumAge;
    }
    calc def CommandApplicable {
        doc /* Parameterized applicability only. Does not grant authority or
         * defeat the consumer's current permission/inhibit. Replay protection,
         * arbitration and clock establishment require separate implementation. */
        in authorityAccepted : Boolean;
        in contextApplicable : Boolean;
        in clockEstablished : Boolean;
        in orderingAccepted : Boolean;
        in issuedAt : TimeValue;
        in validUntil : TimeValue;
        in now : TimeValue;
        return applicable : Boolean = authorityAccepted and contextApplicable and clockEstablished
        and orderingAccepted and issuedAt <= now and now <= validUntil and issuedAt <= validUntil;
    }
    metadata issue : ModelingMetadata::Issue {
        text = "IF-01: Select per-consumer freshness/latency limits from safety and control analysis; cadence does not establish age. IF-02: Establish clock epoch, synchronization uncertainty, producer/authority restart and replay rules. IF-03: Resolve navigation datum, heading/bearing/trim references and required transformations. IF-04: Resolve primary/recovery arbitration, safe inhibits and command expiry. IF-05: Specify physical voltage/current/protection, connector and sealing contracts, storage/telemetry supply and encoding/protocol details. Schema and predicate checks do not close these implementation and physical-evidence gaps.";
    }
}

package BlueDogMethod {
    private import OOSEM::*;
    private import BlueDog::Architecture::*;
    private import ModelingMetadata::refinement;

    doc /* OOSEM organizes engineering artifacts and their engineering questions.
     * Method classification is not verification or evidence acceptance.
     * Existing requirement derivations, refinements and owner constraints keep their
     * meanings. Package roles do not assert a one-level derivation for every member.
     */
    metadata mission : OOSEMPackage about GorgeChallenge {
        kind = OOSEMPackageKind::missionRequirements;
    }
    metadata requirements : OOSEMPackage about BlueDogRequirements {
        kind = OOSEMPackageKind::systemRequirements;
    }
    metadata verificationScope : OOSEMPackage about BlueDogRequirementVerification {
        kind = OOSEMPackageKind::verificationModel;
    }
    metadata simulation : OOSEMPackage about BlueDogMissionSimulation {
        kind = OOSEMPackageKind::analysisModel;
    }
    metadata equipment : OOSEMPackage about BlueDogWindEquipment {
        kind = OOSEMPackageKind::physicalArchitecture;
    }

    metadata logicalArchitecture : OOSEMPackage about BlueDogLogicalArchitecture {
        kind = OOSEMPackageKind::logicalArchitecture;
    }
    metadata physicalArchitecture : OOSEMPackage about BlueDogPhysicalArchitecture {
        kind = OOSEMPackageKind::physicalArchitecture;
    }

    #ioEntity item def WindEstimate {
        attribute frameIdentity : ScalarValues::String;
        item context : BlueDogInterfaceContracts::ObservationContext;
        attribute speed : ISQ::SpeedValue;
        attribute direction : ISQ::AngularMeasureValue;
        attribute observedAt : ISQ::TimeValue;
        attribute valid : ScalarValues::Boolean;
        doc /* Apparent wind in the vessel frame. Timestamp and validity travel with
         * the estimate; accuracy and cadence remain in the wind requirements.
         */
    }
    #ioEntity item def SailingCommand {
        item context : BlueDogInterfaceContracts::CommandContext;
        attribute headingReference : ScalarValues::String;
        attribute sailTrimReference : ScalarValues::String;
        attribute heading : ISQ::AngularMeasureValue;
        attribute sailTrim : ISQ::AngularMeasureValue;
    }
    #ioEntity item def LinkObservation {
        attribute valid : ScalarValues::Boolean;
        item context : BlueDogInterfaceContracts::ObservationContext;
        attribute available : ScalarValues::Boolean;
        attribute observedAt : ISQ::TimeValue;
    }
    #ioEntity item def TelemetryDisposition {
        item record : BlueDogLogicalArchitecture::MissionRecord;
        attribute transmitCurrentRecord : ScalarValues::Boolean;
        attribute retainCriticalRecord : ScalarValues::Boolean;
        doc /* Current records take priority on reconnect; older evidence is
         * retained and transmitted according to the communications requirements. */
    }
    #ioEntity item def DeploymentAssessment {
        attribute configurationIdentity : ScalarValues::String;
        attribute configurationKnown : ScalarValues::Boolean;
        attribute siteAccepted : ScalarValues::Boolean;
        attribute forecastApplicable : ScalarValues::Boolean;
        attribute recoveryPathKnown : ScalarValues::Boolean;
        attribute energyAdmitted : ScalarValues::Boolean;
        attribute requiredSafetyConfirmed : ScalarValues::Boolean;
        doc /* Inputs require configuration-specific inspection and accepted
         * operating/site evidence. The model does not infer these from IC-01 sizing. */
    }
    #ioEntity item def DeploymentPermission {
        attribute configurationIdentity : ScalarValues::String;
        attribute admitted : ScalarValues::Boolean;
    }
    #ioEntity item def ServiceAssessment {
        attribute configurationIdentity : ScalarValues::String;
        attribute sealingEvidenceAccepted : ScalarValues::Boolean;
        attribute actuationEvidenceAccepted : ScalarValues::Boolean;
        attribute configurationRecorded : ScalarValues::Boolean;
    }
    #ioEntity item def RecoveryPlan {
        attribute destinationIdentity : ScalarValues::String;
        attribute routeFeasible : ScalarValues::Boolean;
        attribute requiredEnergy : ISQ::EnergyValue;
        doc /* Reachability and energy are re-evaluated against current conditions.
         * A candidate plan does not establish safe shore access or arrival. */
    }

    @OOSEMPackage { kind = OOSEMPackageKind::logicalArchitecture; }
    package Scenarios {
        doc /* Logical decision-cycle descriptions, not executable controllers.
         * The mission simulation evaluates conceptual implementations. Physical
         * verification must establish the allocated behavior and interfaces.
         */
        action def ObserveWind { out wind : WindEstimate; }
        action def SelectSailingCommand {
            in wind : WindEstimate;
            in navigation : BlueDogLogicalArchitecture::NavigationEstimate;
            in permission : BlueDogLogicalArchitecture::OperationPermission [1];
            out command : SailingCommand;
        }
        action def ApplySailingCommand {
            in command : SailingCommand [1];
            in permission : BlueDogLogicalArchitecture::OperationPermission [1];
            doc /* Apply only with current supervisor permission at the actuation
             * interface. This sequence does not bypass the independent inhibit. */
        }
        #logicalScenario action def NormalSailing {
            in navigation : BlueDogLogicalArchitecture::NavigationEstimate;
            in permission : BlueDogLogicalArchitecture::OperationPermission [1];
            doc /* One cycle with valid navigation, wind and safety capabilities.
             * Invalid observations transfer responsibility to degraded-operation logic.
             */
            action observe : ObserveWind;
            then action select : SelectSailingCommand;
            then action actuate : ApplySailingCommand;
            flow observe.wind to select.wind;
            bind select.navigation = navigation;
            bind select.permission = permission;
            bind actuate.permission = permission;
            flow select.command to actuate.command;
        }
        action def ObserveTraffic { out observation : BlueDogLogicalArchitecture::TrafficObservation; }
        action def ObserveNavigation { out navigation : BlueDogLogicalArchitecture::NavigationEstimate; }
        action def AssessEncounter {
            in observation : BlueDogLogicalArchitecture::TrafficObservation;
            in navigation : BlueDogLogicalArchitecture::NavigationEstimate;
            out assessment : BlueDogLogicalArchitecture::TrafficAssessment;
        }
        action def SelectAvoidanceManeuver {
            in assessment : BlueDogLogicalArchitecture::TrafficAssessment;
            in navigation : BlueDogLogicalArchitecture::NavigationEstimate;
            in permission : BlueDogLogicalArchitecture::OperationPermission [1];
            out command : SailingCommand;
        }
        action def ExecuteAndReassess {
            in command : SailingCommand [1];
            in permission : BlueDogLogicalArchitecture::OperationPermission [1];
            out assessment : BlueDogLogicalArchitecture::TrafficAssessment;
        }
        #logicalScenario action def TrafficEncounter {
            in permission : BlueDogLogicalArchitecture::OperationPermission [1];
            doc /* Repeated encounter assessment includes AIS and non-AIS traffic.
             * Detection failure invokes abort/recovery; this sequence alone does not
             * establish collision avoidance or navigation-rule compliance.
             */
            action observe : ObserveTraffic;
            then action navigate : ObserveNavigation;
            then action assess : AssessEncounter;
            then action select : SelectAvoidanceManeuver;
            then action execute : ExecuteAndReassess;
            flow observe.observation to assess.observation;
            flow navigate.navigation to assess.navigation;
            flow assess.assessment to select.assessment;
            flow navigate.navigation to select.navigation;
            bind select.permission = permission;
            bind execute.permission = permission;
            flow select.command to execute.command;
        }
        action def LatchAbort {
            out permission : BlueDogLogicalArchitecture::OperationPermission;
            out record : BlueDogLogicalArchitecture::MissionRecord;
        }
        action def RecordAndSignalAbort {
            in record : BlueDogLogicalArchitecture::MissionRecord;
            doc /* Queue an alert and retain local evidence without waiting for a
             * communications link or acknowledgment before proceeding to recovery.
             */
        }
        action def AssessRecoveryBoundary {
            in navigation : BlueDogLogicalArchitecture::NavigationEstimate;
            out boundary : BlueDogLogicalArchitecture::BoundaryAssessment;
        }
        action def SelectReachableShore {
            in navigation : BlueDogLogicalArchitecture::NavigationEstimate;
            in observation : BlueDogLogicalArchitecture::TrafficObservation;
            in boundary : BlueDogLogicalArchitecture::BoundaryAssessment;
            in reserve : BlueDogLogicalArchitecture::ReserveAssessment;
            in permission : BlueDogLogicalArchitecture::OperationPermission [1];
            out plan : RecoveryPlan;
        }
        action def RecoverAndReassess {
            in plan : RecoveryPlan;
            in permission : BlueDogLogicalArchitecture::OperationPermission [1];
            out command : BlueDogLogicalArchitecture::RecoveryCommand;
            out record : BlueDogLogicalArchitecture::MissionRecord;
        }
        action def PersistRecoveryAuthorization {
            in record : BlueDogLogicalArchitecture::MissionRecord;
            out authorizationStored : ScalarValues::Boolean [1];
            doc /* Confirm durable disqualification storage before motor enable.
             * Failure or unknown acknowledgment cannot authorize propulsion.
             * This descriptive step does not implement storage hardware. */
        }
        action def ApplyRecoveryCommand {
            in command : BlueDogLogicalArchitecture::RecoveryCommand [1];
            in permission : BlueDogLogicalArchitecture::OperationPermission [1];
            in authorizationStored : ScalarValues::Boolean [1];
            out record : BlueDogLogicalArchitecture::MissionRecord;
            doc /* Check current authority, command applicability, qualification,
             * durable state and interlocks before enable. Record the observed
             * execution disposition; acceptance does not establish shore arrival. */
        }
        action def RecordRecoveryOutcome {
            in record : BlueDogLogicalArchitecture::MissionRecord;
        }
        #logicalScenario action def AbortAndRecover {
            doc /* A safety-capability loss, reserve trigger or other declared abort
             * condition ends the attempt. Recovery may use the motor and must remain
             * autonomous through communications loss. Reassess shore reachability
             * and safety throughout recovery; completion never resumes the attempt.
             */
            action abort : LatchAbort;
            then action signal : RecordAndSignalAbort;
            then action navigate : ObserveNavigation;
            then action observe : ObserveTraffic;
            then action boundary : AssessRecoveryBoundary;
            then action reserve : ObserveReserve;
            then action plan : SelectReachableShore;
            then action recover : RecoverAndReassess;
            then action persist : PersistRecoveryAuthorization;
            then action actuate : ApplyRecoveryCommand;
            then action record : RecordRecoveryOutcome;
            flow navigate.navigation to boundary.navigation;
            flow navigate.navigation to plan.navigation;
            flow observe.observation to plan.observation;
            flow boundary.boundary to plan.boundary;
            flow reserve.assessment to plan.reserve;
            flow recover.command to actuate.command;
            flow recover.record to persist.record;
            flow persist.authorizationStored to actuate.authorizationStored;
            flow abort.permission to actuate.permission;
            flow actuate.record to record.record;
            flow abort.record to signal.record;
            flow abort.permission to plan.permission;
            flow abort.permission to recover.permission;
            flow plan.plan to recover.plan;
        }
        action def ObserveCapsizeSafety {
            out observation : BlueDogLogicalArchitecture::SafetyObservation;
        }
        action def AssessCapsizeContinuation {
            in observation : BlueDogLogicalArchitecture::SafetyObservation;
            out permission : BlueDogLogicalArchitecture::OperationPermission;
            out record : BlueDogLogicalArchitecture::MissionRecord;
            doc /* Preserve the qualification and abort latches. Inversion alone
             * does not disqualify. Missing safety confirmation, intervention or
             * motor use prohibits resumption. An explicit unassisted upright
             * control observation is required before sailing can resume. */
        }
        action def ApplyCapsizePermission {
            in permission : BlueDogLogicalArchitecture::OperationPermission [1];
        }
        action def RetainCapsizeRecord {
            in record : BlueDogLogicalArchitecture::MissionRecord;
        }
        #logicalScenario action def CapsizeAndResume {
            doc /* One repeated capsize-management decision cycle, not a promise
             * that the hull will self-right. Suspend sailing and gate scoring,
             * observe required safety while inverted, then either retain the
             * attempt until unassisted righting or transfer to AbortAndRecover.
             * The native supervisor executes permissions; physical righting,
             * inverted safety and restoration times still require measurement. */
            action observe : ObserveCapsizeSafety;
            then action assess : AssessCapsizeContinuation;
            then action apply : ApplyCapsizePermission;
            then action record : RetainCapsizeRecord;
            flow observe.observation to assess.observation;
            flow assess.permission to apply.permission;
            flow assess.record to record.record;
        }
        action def ValidateNavigation {
            in observation : BlueDogLogicalArchitecture::NavigationEstimate;
            out current : BlueDogLogicalArchitecture::NavigationEstimate;
            out usable : ScalarValues::Boolean [1];
            doc /* Preserve the producer assertion and report consumer usability
             * separately using the allocated age/context criteria. Backup safety
             * confirmation is a separate observation, not inferred from this flag. */
        }
        action def SelectNavigationGuidance {
            in navigation : BlueDogLogicalArchitecture::NavigationEstimate;
            in navigationUsable : ScalarValues::Boolean [1];
            in permission : BlueDogLogicalArchitecture::OperationPermission [1];
            out command : SailingCommand;
            doc /* Invalid navigation cannot authorize a sailing command; the
             * separate supervisor permission interface inhibits actuation. */
        }
        #logicalScenario action def NavigationUpdate {
            in permission : BlueDogLogicalArchitecture::OperationPermission [1];
            doc /* Observe, validate, guide and actuate. Invalid primary navigation
             * enters degraded operation; continuation requires separately confirmed
             * safety and cannot credit gate progress from invalid observations. */
            action observe : ObserveNavigation;
            then action validate : ValidateNavigation;
            then action guide : SelectNavigationGuidance;
            then action actuate : ApplySailingCommand;
            flow observe.navigation to validate.observation;
            flow validate.current to guide.navigation;
            flow validate.usable to guide.navigationUsable;
            bind guide.permission = permission;
            bind actuate.permission = permission;
            flow guide.command to actuate.command;
        }
        action def ObserveLink { out link : LinkObservation; }
        action def ReadCurrentRecord { out record : BlueDogLogicalArchitecture::MissionRecord; }
        action def SelectTelemetryDisposition {
            in link : LinkObservation;
            in record : BlueDogLogicalArchitecture::MissionRecord;
            out disposition : TelemetryDisposition;
        }
        action def SendOrRetainRecord { in disposition : TelemetryDisposition; }
        #logicalScenario action def CommunicationsOutage {
            doc /* One repeated link-state decision cycle through outage and
             * reconnection. Autonomous safety continues without waiting for a link;
             * retain critical records and deliver current status before backlog
             * when service returns. No operator control is inferred from monitoring. */
            action observe : ObserveLink;
            then action read : ReadCurrentRecord;
            then action select : SelectTelemetryDisposition;
            then action deliver : SendOrRetainRecord;
            flow observe.link to select.link;
            flow read.record to select.record;
            flow select.disposition to deliver.disposition;
        }
        action def ObserveReserve { out assessment : BlueDogLogicalArchitecture::ReserveAssessment; }
        action def SelectReserveResponse {
            in assessment : BlueDogLogicalArchitecture::ReserveAssessment;
            out permission : BlueDogLogicalArchitecture::OperationPermission;
            out recovery : BlueDogLogicalArchitecture::RecoveryCommand;
        }
        action def PreserveSafetyLoads { in permission : BlueDogLogicalArchitecture::OperationPermission [1]; }
        action def RequestRecovery { in command : BlueDogLogicalArchitecture::RecoveryCommand [1]; }
        #logicalScenario action def LowEnergyResponse {
            doc /* Compare conservative usable energy with current recovery demand,
             * protect required safety loads, and abort when the protected reserve
             * is threatened. Recovery action is conditional on the resulting
             * command and available authority; energy restoration cannot clear abort. */
            action observe : ObserveReserve;
            then action select : SelectReserveResponse;
            then action preserve : PreserveSafetyLoads;
            then action request : RequestRecovery;
            flow observe.assessment to select.assessment;
            flow select.permission to preserve.permission;
            flow select.recovery to request.command;
        }
        action def InspectLaunchReadiness { out assessment : DeploymentAssessment; }
        action def AdmitLaunch {
            in assessment : DeploymentAssessment;
            out permission : DeploymentPermission;
        }
        action def LaunchAndInitialize { in permission : DeploymentPermission; }
        #logicalScenario action def PrepareAndLaunch {
            doc /* The operator supplies inspected configuration and accepted site,
             * forecast, safety and energy assessments. Admission precedes physical
             * launch and initialization of a new attempt. Transport and launch are
             * operator actions; onboard autonomy starts at the declared mission boundary. */
            action inspect : InspectLaunchReadiness;
            then action admit : AdmitLaunch;
            then action launch : LaunchAndInitialize;
            flow inspect.assessment to admit.assessment;
            flow admit.permission to launch.permission;
        }
        action def ServiceAndInspect { out assessment : ServiceAssessment; }
        action def AssessServiceRelease {
            in assessment : ServiceAssessment;
            out permission : DeploymentPermission;
        }
        action def RecordServiceConfiguration {
            in assessment : ServiceAssessment;
            in permission : DeploymentPermission;
        }
        #logicalScenario action def MaintainAndRelease {
            doc /* After component replacement, the operator inspects sealing and
             * actuation and records the actual configuration before release.
             * A denied release is recorded too; this descriptive scenario does
             * not execute or accept physical service tests. */
            action service : ServiceAndInspect;
            then action assess : AssessServiceRelease;
            then action record : RecordServiceConfiguration;
            flow service.assessment to assess.assessment;
            flow service.assessment to record.assessment;
            flow assess.permission to record.permission;
        }
        #logicalScenario action normalSailing : NormalSailing;
        #logicalScenario action trafficEncounter : TrafficEncounter;
        #logicalScenario action abortAndRecover : AbortAndRecover;
        #logicalScenario action capsizeAndResume : CapsizeAndResume;
        #logicalScenario action navigationUpdate : NavigationUpdate;
        #logicalScenario action communicationsOutage : CommunicationsOutage;
        #logicalScenario action lowEnergyResponse : LowEnergyResponse;
        #logicalScenario action prepareAndLaunch : PrepareAndLaunch;
        #logicalScenario action maintainAndRelease : MaintainAndRelease;

        allocate normalSailing.observe to BlueDogLogicalArchitecture::vessel.wind;
        allocate normalSailing.select to BlueDogLogicalArchitecture::vessel.guidance;
        allocate normalSailing.actuate to BlueDogLogicalArchitecture::vessel.actuation;
        allocate trafficEncounter.observe to BlueDogLogicalArchitecture::vessel.trafficObservation;
        allocate trafficEncounter.navigate to BlueDogLogicalArchitecture::vessel.navigation;
        allocate trafficEncounter.assess to BlueDogLogicalArchitecture::vessel.collision;
        allocate trafficEncounter.select to BlueDogLogicalArchitecture::vessel.guidance;
        allocate trafficEncounter.execute to BlueDogLogicalArchitecture::vessel.actuation;
        allocate abortAndRecover.abort to BlueDogLogicalArchitecture::vessel.supervision;
        allocate abortAndRecover.signal to BlueDogLogicalArchitecture::vessel.communications;
        allocate abortAndRecover.signal to BlueDogLogicalArchitecture::vessel.recording;
        allocate abortAndRecover.plan to BlueDogLogicalArchitecture::vessel.recovery;
        allocate abortAndRecover.recover to BlueDogLogicalArchitecture::vessel.recovery;
        allocate abortAndRecover.navigate to BlueDogLogicalArchitecture::vessel.navigation;
        allocate abortAndRecover.observe to BlueDogLogicalArchitecture::vessel.trafficObservation;
        allocate abortAndRecover.boundary to BlueDogLogicalArchitecture::vessel.boundary;
        allocate abortAndRecover.reserve to BlueDogLogicalArchitecture::vessel.energy;
        allocate abortAndRecover.persist to BlueDogLogicalArchitecture::vessel.recording;
        allocate abortAndRecover.actuate to BlueDogLogicalArchitecture::vessel.recoveryActuation;
        allocate abortAndRecover.record to BlueDogLogicalArchitecture::vessel.recording;
        allocate capsizeAndResume.observe to BlueDogLogicalArchitecture::vessel.safety;
        allocate capsizeAndResume.assess to BlueDogLogicalArchitecture::vessel.supervision;
        allocate capsizeAndResume.apply to BlueDogLogicalArchitecture::vessel.actuation;
        allocate capsizeAndResume.record to BlueDogLogicalArchitecture::vessel.recording;
        allocate navigationUpdate.observe to BlueDogLogicalArchitecture::vessel.navigation;
        allocate navigationUpdate.validate to BlueDogLogicalArchitecture::vessel.navigation;
        allocate navigationUpdate.guide to BlueDogLogicalArchitecture::vessel.guidance;
        allocate navigationUpdate.actuate to BlueDogLogicalArchitecture::vessel.actuation;
        allocate communicationsOutage.observe to BlueDogLogicalArchitecture::vessel.communications;
        allocate communicationsOutage.read to BlueDogLogicalArchitecture::vessel.recording;
        allocate communicationsOutage.select to BlueDogLogicalArchitecture::vessel.communications;
        allocate communicationsOutage.deliver to BlueDogLogicalArchitecture::vessel.communications;
        allocate lowEnergyResponse.observe to BlueDogLogicalArchitecture::vessel.energy;
        allocate lowEnergyResponse.select to BlueDogLogicalArchitecture::vessel.supervision;
        allocate lowEnergyResponse.preserve to BlueDogLogicalArchitecture::vessel.energy;
        allocate lowEnergyResponse.request to BlueDogLogicalArchitecture::vessel.recovery;
        allocate prepareAndLaunch.inspect to missionContext.operator;
        allocate prepareAndLaunch.admit to BlueDogLogicalArchitecture::vessel.supervision;
        allocate prepareAndLaunch.launch to missionContext.operator;
        allocate maintainAndRelease.service to missionContext.operator;
        allocate maintainAndRelease.assess to missionContext.operator;
        allocate maintainAndRelease.record to BlueDogLogicalArchitecture::vessel.recording;

        #refinement dependency normalScenario from NormalSailing to BlueDogUseCases::sailGorge;
        #refinement dependency trafficScenario from TrafficEncounter to BlueDogUseCases::avoidTraffic;
        #refinement dependency recoveryScenario from AbortAndRecover to BlueDogUseCases::recover;
        #refinement dependency capsizeScenario from CapsizeAndResume to BlueDogUseCases::recoverUpright;
        #refinement dependency navigationScenario from NavigationUpdate to BlueDogUseCases::navigateCourse;
        #refinement dependency outageScenario from CommunicationsOutage to BlueDogUseCases::monitor;
        #refinement dependency energyScenario from LowEnergyResponse to BlueDogUseCases::preserveRecoveryReserve;
        #refinement dependency launchScenario from PrepareAndLaunch to BlueDogUseCases::prepare;
        #refinement dependency serviceScenario from MaintainAndRelease to BlueDogUseCases::maintain;
        dependency normalEvidence from BlueDogRequirementVerification::NavigationAndControlVerification to NormalSailing;
        dependency trafficEvidence from BlueDogRequirementVerification::TrafficSafetyVerification to TrafficEncounter;
        dependency recoveryEvidence from BlueDogRequirementVerification::EmergencyControlVerification to AbortAndRecover;
        dependency recoveryPropulsionEvidence from BlueDogRequirementVerification::RecoveryPropulsionVerification to AbortAndRecover;
        dependency recoveryReserveEvidence from BlueDogRequirementVerification::RecoveryEnergyVerification to AbortAndRecover;
        dependency capsizeEvidence from BlueDogRequirementVerification::CapsizeControlRecoveryVerification to CapsizeAndResume;
        dependency navigationEvidence from BlueDogRequirementVerification::NavigationAvailabilityVerification to NavigationUpdate;
        dependency outageEvidence from BlueDogRequirementVerification::CommunicationsVerification to CommunicationsOutage;
        dependency reserveEvidence from BlueDogRequirementVerification::LowEnergyRecoveryVerification to LowEnergyResponse;
        dependency serviceEvidence from BlueDogRequirementVerification::ServiceabilityVerification to MaintainAndRelease;
        dependency simulationScope from BlueDogMissionSimulation::Inputs to NormalSailing;
        dependency encounterSimulationScope from BlueDogMissionSimulation::Inputs to TrafficEncounter;
        dependency recoverySimulationScope from BlueDogMissionSimulation::Inputs to AbortAndRecover;
    }
}

package BlueDogMissionLogic {
    private import ScalarValues::*;
    private import ModelingMetadata::refinement;

    doc /* Executable supervisory policy for the conceptual mission simulator.
     * Geometry, sensing observations, heading search and vessel dynamics are supplied
     * by the simulator. These actions do not implement a physical autopilot.
     */
    action def HandleEvent {
        in eventKind : String;
        in qualificationLost : Boolean = false;
        out directive : String;
        out capsized : Boolean;
        out recoveryPermitted : Boolean;
        out qualificationLostNext : Boolean;
        first start;
        then action classify {
            assign directive :=
                if eventKind == "operator_intervention" or eventKind == "manual_weather_update" or eventKind == "motor_use" ? "disqualify"
            else if eventKind == "communications_loss" ? "communications_outage"
            else if eventKind == "weather_service_loss" ? "retain_forecast"
            else if eventKind == "wind_sensor_loss" ? "wind_outage"
            else if eventKind == "navigation_loss" ? "navigation_outage"
            else if eventKind == "capsize" or eventKind == "unassisted_righting" ? "assess_capsize"
            else if eventKind == "forecast_invalidated" or eventKind == "sensing_loss" or eventKind == "steering_loss" or eventKind == "power_loss" or eventKind == "safety_capability_loss" or eventKind == "refuge_entry" or eventKind == "grounding" or eventKind == "anchoring" or eventKind == "shore_attachment" ? "abort"
            else if eventKind == "terminal_failure" ? "stop"
            else "unsupported";
            assign capsized := eventKind == "capsize";
            assign recoveryPermitted := eventKind == "sensing_loss" or eventKind == "forecast_invalidated" or eventKind == "safety_capability_loss" or eventKind == "capsize";
            assign qualificationLostNext := qualificationLost or directive == "disqualify" or directive == "abort";
        }
        then done;
    }

    action def CapsizeDisposition {
        doc /* Explicit observation contract, not a righting dynamics prediction.
         * Safety must remain available while inverted. Resumption additionally
         * requires observed unassisted upright recovery and restored control.
         * Missing safety evidence fails closed; a prior abort cannot be cleared. */
        in currentlyCapsized : Boolean;
        in uprightRecoveryObserved : Boolean;
        in requiredSafetyConfirmed : Boolean;
        in abortLatched : Boolean;
        in qualificationLost : Boolean = false;
        out directive : String;
        out qualificationLostNext : Boolean;
        first start;
        then action assess {
            assign directive := if abortLatched or qualificationLost or not requiredSafetyConfirmed ? "abort"
            else if uprightRecoveryObserved and not currentlyCapsized ? "invalid_observation"
            else if uprightRecoveryObserved ? "resume"
            else "await_righting";
            assign qualificationLostNext := qualificationLost or abortLatched or not requiredSafetyConfirmed;
        }
        then done;
    }
    dependency capsizeQualification from CapsizeDisposition to BlueDogRequirements::capsizeQualificationRetention;
    #refinement dependency capsizeScenarioPolicy from CapsizeDisposition to BlueDogMethod::Scenarios::AssessCapsizeContinuation;

    action def SupervisoryCycle {
        doc /* A nominal upright cycle assumes valid observations supplied by its caller.
         * Inversion or invalid primary navigation requires explicit confirmation of
         * retained safety capability. Qualification and safety abort are distinct
         * persistent states: intervention ends qualification even without a casualty.
         * The caller supplies geometry and energy assessments; this action owns the
         * response permissions. It does not predict righting or verify hardware. */
        in windValid : Boolean;
        in navigationValid : Boolean = true;
        in capsized : Boolean = false;
        in requiredSafetyConfirmed : Boolean;
        in reserveThreatened : Boolean = false;
        in trafficConflict : Boolean;
        in abortRequested : Boolean;
        in abortLatched : Boolean;
        in qualificationLost : Boolean = false;
        in communicationsAvailable : Boolean;
        out abortLatchedNext : Boolean;
        out qualificationLostNext : Boolean;
        out sailingPermitted : Boolean;
        out gateScoringPermitted : Boolean;
        out harvestPermitted : Boolean;
        out mode : String;
        out alert : String;
        first start;
        then action chooseMode {
            assign abortLatchedNext := abortLatched or abortRequested or reserveThreatened or not requiredSafetyConfirmed;
            assign qualificationLostNext := qualificationLost or abortLatchedNext;
            assign sailingPermitted := windValid and navigationValid and not capsized and not qualificationLostNext;
            assign gateScoringPermitted := navigationValid and not capsized and not qualificationLostNext;
            assign harvestPermitted := not capsized;
            assign mode := if abortLatchedNext ? "abort_recovery"
            else if qualificationLostNext ? "disqualified"
            else if capsized ? "capsized_drift"
            else if not navigationValid ? "navigation_degraded"
            else if not windValid ? "degraded_drift"
            else if trafficConflict ? "traffic_avoidance"
            else "sailing";
            assign alert := if not abortLatchedNext or abortLatched ? "none"
            else if communicationsAvailable ? "attempt" else "queue";
        }
        then done;
    }

    action def RecoveryAuthority {
        in eventKind : String;
        in ordinaryPermission : Boolean;
        in independentPath : Boolean;
        out permitted : Boolean;
        first start;
        then action chooseAuthority {
            assign permitted := ordinaryPermission or (independentPath and (eventKind == "steering_loss" or eventKind == "power_loss"));
        }
        then done;
    }
    action def FallbackPolicy {
        in recoveryAvailable : Boolean;
        in recoveryPermitted : Boolean;
        out attemptRecovery : Boolean;
        out continueDrift : Boolean;
        first start;
        then action chooseFallback {
            assign attemptRecovery := recoveryAvailable and recoveryPermitted;
            assign continueDrift := not (recoveryAvailable and recoveryPermitted);
        }
        then done;
    }
    dependency fallbackBasis from FallbackPolicy to GorgeChallenge::autonomousShoreRecovery;

    dependency unassisted from HandleEvent to GorgeChallenge::unassistedAttempt;
    dependency propulsion from HandleEvent to GorgeChallenge::sailingPropulsion;
    dependency safeRecovery from SupervisoryCycle to GorgeChallenge::autonomousShoreRecovery;
    dependency normalScenario from SupervisoryCycle to BlueDogMethod::Scenarios::NormalSailing;
    dependency trafficScenario from SupervisoryCycle to BlueDogMethod::Scenarios::TrafficEncounter;
    dependency recoveryScenario from SupervisoryCycle to BlueDogMethod::Scenarios::AbortAndRecover;
    action supervisor : SupervisoryCycle;
    action capsizeDisposition : CapsizeDisposition;
    action recoveryAuthority : RecoveryAuthority;
    action fallback : FallbackPolicy;
    allocate recoveryAuthority to BlueDogLogicalArchitecture::vessel.recovery;
    allocate fallback to BlueDogLogicalArchitecture::vessel.recovery;
    dependency recoveryAuthorityScenario from RecoveryAuthority to BlueDogMethod::Scenarios::AbortAndRecover;
    dependency fallbackScenario from FallbackPolicy to BlueDogMethod::Scenarios::AbortAndRecover;
    allocate supervisor to BlueDogLogicalArchitecture::vessel.supervision;
    allocate capsizeDisposition to BlueDogLogicalArchitecture::vessel.supervision;
}

package BlueDogRequirementBasis {
    private import ScalarValues::*;
    enum def Kind { ownerConstraint; functionalAcceptance; performanceAllocation; selectedStrategy; studyObjective; assuranceObligation; }
    metadata def Basis {
        attribute kind : Kind;
        attribute rationale : String;
    }
    metadata def StudyObjective :> Basis {
        attribute :>> kind = Kind::studyObjective;
    }
    metadata basis0 : Basis about BlueDogRequirements::DesktopManufacture { kind = Kind::ownerConstraint; rationale = "Explicit owner choices; retain independently of challenge-derived performance."; }
    metadata basis1 : Basis about BlueDogRequirements::Transportability { kind = Kind::ownerConstraint; rationale = "Explicit owner choices; retain independently of challenge-derived performance."; }
    metadata basis2 : Basis about BlueDogStructure::HybridConstruction { kind = Kind::ownerConstraint; rationale = "Explicit owner choices; retain independently of challenge-derived performance."; }
    metadata basis3 : Basis about BlueDogStructure::BendingStrength { kind = Kind::functionalAcceptance; rationale = "Verify the actual design against qualified evidence and applicable functional/load/site limits; provisional screening constants are not acceptance thresholds."; }
    metadata basis4 : Basis about BlueDogStructure::PanelStrength { kind = Kind::functionalAcceptance; rationale = "Verify the actual design against qualified evidence and applicable functional/load/site limits; provisional screening constants are not acceptance thresholds."; }
    metadata basis5 : Basis about BlueDogStructure::WetCouponStrength { kind = Kind::functionalAcceptance; rationale = "Verify the actual design against qualified evidence and applicable functional/load/site limits; provisional screening constants are not acceptance thresholds."; }
    metadata basis6 : Basis about BlueDogStructure::WetCouponStiffness { kind = Kind::functionalAcceptance; rationale = "Verify the actual design against qualified evidence and applicable functional/load/site limits; provisional screening constants are not acceptance thresholds."; }
    metadata basis7 : Basis about BlueDogStructure::AppendageDeflection { kind = Kind::functionalAcceptance; rationale = "Verify the actual design against qualified evidence and applicable functional/load/site limits; provisional screening constants are not acceptance thresholds."; }
    metadata basis8 : Basis about BlueDogStructure::HullDeflection { kind = Kind::functionalAcceptance; rationale = "Verify the actual design against qualified evidence and applicable functional/load/site limits; provisional screening constants are not acceptance thresholds."; }
    metadata basis9 : Basis about BlueDogStructure::PanelDeflection { kind = Kind::functionalAcceptance; rationale = "Verify the actual design against qualified evidence and applicable functional/load/site limits; provisional screening constants are not acceptance thresholds."; }
    metadata basis10 : Basis about BlueDogStructure::LoadedFreeboard { kind = Kind::functionalAcceptance; rationale = "Verify the actual design against qualified evidence and applicable functional/load/site limits; provisional screening constants are not acceptance thresholds."; }
    metadata basis11 : Basis about BlueDogStructure::ReserveBuoyancy { kind = Kind::functionalAcceptance; rationale = "Verify the actual design against qualified evidence and applicable functional/load/site limits; provisional screening constants are not acceptance thresholds."; }
    metadata basis12 : Basis about BlueDogStructure::LaunchClearance { kind = Kind::functionalAcceptance; rationale = "Verify the actual design against qualified evidence and applicable functional/load/site limits; provisional screening constants are not acceptance thresholds."; }
    metadata basis13 : Basis about BlueDogStructure::PrintTileEnvelope { kind = Kind::functionalAcceptance; rationale = "Verify the actual design against qualified evidence and applicable functional/load/site limits; provisional screening constants are not acceptance thresholds."; }
    metadata basis14 : Basis about BlueDogRequirements::PrintedMaterialAging { kind = Kind::functionalAcceptance; rationale = "Verify the actual design against qualified evidence and applicable functional/load/site limits; provisional screening constants are not acceptance thresholds."; }
    metadata basis15 : Basis about BlueDogRequirements::SelfRighting { kind = Kind::selectedStrategy; rationale = "Selected passive-righting concept; the challenge permits qualified limp recovery instead."; }
    metadata basis16 : Basis about BlueDogRequirements::LiftMass { kind = Kind::performanceAllocation; rationale = "Retained measurable performance allocation. The mission motivates the function, not this exact number; confirm the allocation through handling/control/mission evidence before design release."; }
    metadata basis17 : Basis about BlueDogRequirements::SetupDuration { kind = Kind::performanceAllocation; rationale = "Retained measurable performance allocation. The mission motivates the function, not this exact number; confirm the allocation through handling/control/mission evidence before design release."; }
    metadata basis18 : Basis about BlueDogRequirements::PackDuration { kind = Kind::performanceAllocation; rationale = "Retained measurable performance allocation. The mission motivates the function, not this exact number; confirm the allocation through handling/control/mission evidence before design release."; }
    metadata basis19 : Basis about BlueDogRequirements::WindSampleCadence { kind = Kind::performanceAllocation; rationale = "Retained measurable performance allocation. The mission motivates the function, not this exact number; confirm the allocation through handling/control/mission evidence before design release."; }
    metadata basis20 : Basis about BlueDogRequirements::WindSpeedAccuracy { kind = Kind::performanceAllocation; rationale = "Retained measurable performance allocation. The mission motivates the function, not this exact number; confirm the allocation through handling/control/mission evidence before design release."; }
    metadata basis21 : Basis about BlueDogRequirements::WindDirectionAccuracy { kind = Kind::performanceAllocation; rationale = "Retained measurable performance allocation. The mission motivates the function, not this exact number; confirm the allocation through handling/control/mission evidence before design release."; }
    metadata basis22 : Basis about BlueDogRequirements::PositionAccuracy { kind = Kind::performanceAllocation; rationale = "Retained measurable performance allocation. The mission motivates the function, not this exact number; confirm the allocation through handling/control/mission evidence before design release."; }
    metadata basis23 : Basis about BlueDogRequirements::HeadingAccuracy { kind = Kind::performanceAllocation; rationale = "Retained measurable performance allocation. The mission motivates the function, not this exact number; confirm the allocation through handling/control/mission evidence before design release."; }
    metadata basis24 : Basis about BlueDogRequirements::RightingDeadline { kind = Kind::performanceAllocation; rationale = "Retained measurable performance allocation. The mission motivates the function, not this exact number; confirm the allocation through handling/control/mission evidence before design release."; }
    part materials : BlueDogDesignDecisions::Decision {
        attribute :>> disposition = "10 GPa and 50 MPa remain unverified numerical inputs. Qualification may credit only supported wet/jointed material bounds; resize for measured properties.";
        attribute :>> evidenceNeeded = "Directional production coupons, exposure, joint/process variability and conservative allowable/stiffness bounds.";
    }
    part structuralScreens : BlueDogDesignDecisions::Decision {
        attribute :>> disposition = "Keep the numerical screening policy explicit: 2/0.5/1 percent deflection, 10 kPa pressure, 100 N proof probe, 50 mm freeboard and 100 percent intact reserve are provisional study controls.";
        attribute :>> evidenceNeeded = "Mission load cases, deformed-foil/control and sealing/clearance sensitivity, attachment loads and casualty flotation. Screen passes do not close these requirements.";
    }
    part manufactureAndSites : BlueDogDesignDecisions::Decision {
        attribute :>> disposition = "250 mm print jobs and one-person handling remain owner constraints. A 230 mm tile and a 1.5 m launch depth with 0.3 m clearance are changeable analysis assumptions.";
        attribute :>> evidenceNeeded = "Sliced job envelopes including supports and actual site/depth/appendage clearance evidence.";
    }
    part aging : BlueDogDesignDecisions::Decision {
        attribute :>> disposition = "Accept aged material against the capacity credited to the design, not 80 percent of an unaged coupon. Establish mission-representative exposure; 300 MJ/m2 was an unvalidated accelerated-test dose.";
        attribute :>> evidenceNeeded = "Exposure equivalence and aged production-component load bounds; no relative-retention target substitutes for structural adequacy.";
    }
    part retainedAllocations : BlueDogDesignDecisions::Decision {
        attribute :>> disposition = "Retain safety behavior, environmental qualification profiles, sensing/control timing and accuracy, handling targets and the provisional mission-reliability objective. These are performance allocations, not material or architecture mandates.";
        attribute :>> evidenceNeeded = "Validation of the allocated numbers against handling, control sensitivity and mission/encounter analysis; they are not uniquely derived by arithmetic from the challenge.";
    }
    part recoveryStrategy : BlueDogDesignDecisions::Decision {
        attribute :>> disposition = "Treat passive self-righting as a selected vehicle strategy. The Gorge challenge also admits demonstrated autonomous limp recovery after abort.";
        attribute :>> evidenceNeeded = "Concept-specific capsize and shore-recovery demonstrations, including impaired equipment; retain current numerical recovery screens without claiming universal necessity.";
    }
    dependency materialStudy from materials to BlueDogStructuralBasis::Inputs;
    dependency materialAcceptance from materials to BlueDogStructure::wetCouponStiffness;
    dependency strengthAcceptance from materials to BlueDogStructure::wetCouponStrength;
    dependency screenPurpose from structuralScreens to BlueDogStructure::structuralIntegrity;
    dependency printerChoice from manufactureAndSites to BlueDogRequirements::desktopManufacture;
    dependency agedCapacity from aging to BlueDogRequirements::printedMaterialAging;
    dependency rightingChoice from recoveryStrategy to BlueDogRequirements::selfRighting;

    metadata basisServiceability : Basis about BlueDogRequirements::Serviceability { kind = Kind::ownerConstraint; rationale = "Between-deployment access and replacement are owner lifecycle constraints; successful unassisted passage does not imply serviceability."; }
    metadata basisMissionSuccessProbability : StudyObjective about BlueDogRequirements::MissionSuccessProbability { rationale = "Provisional reliability-study objective. Its numerical target and distribution assumptions do not govern finite Gorge qualification and require an accepted mission-specific evidence basis before adoption."; }
    metadata basisFailureRateBudget : StudyObjective about BlueDogRequirements::FailureRateBudget { rationale = "Provisional reliability-study objective. Its numerical target and distribution assumptions do not govern finite Gorge qualification and require an accepted mission-specific evidence basis before adoption."; }
    metadata basisCapsizeControlRecovery : Basis about BlueDogRequirements::CapsizeControlRecovery { kind = Kind::selectedStrategy; rationale = "Acceptance belongs to the selected N-051 passive-righting campaign. The independent challenge admits qualified post-abort limp recovery; this does not impose passive righting on every candidate architecture."; }
    metadata basisCapsizeRigRetention : Basis about BlueDogRequirements::CapsizeRigRetention { kind = Kind::selectedStrategy; rationale = "Acceptance belongs to the selected N-051 passive-righting campaign. The independent challenge admits qualified post-abort limp recovery; this does not impose passive righting on every candidate architecture."; }
    metadata basisCapsizeBallastRetention : Basis about BlueDogRequirements::CapsizeBallastRetention { kind = Kind::selectedStrategy; rationale = "Acceptance belongs to the selected N-051 passive-righting campaign. The independent challenge admits qualified post-abort limp recovery; this does not impose passive righting on every candidate architecture."; }
    metadata basisCapsizeElectronicsSealing : Basis about BlueDogRequirements::CapsizeElectronicsSealing { kind = Kind::selectedStrategy; rationale = "Acceptance belongs to the selected N-051 passive-righting campaign. The independent challenge admits qualified post-abort limp recovery; this does not impose passive righting on every candidate architecture."; }
    metadata basisControlRecoveryDeadline : Basis about BlueDogRequirements::ControlRecoveryDeadline { kind = Kind::selectedStrategy; rationale = "Acceptance belongs to the selected N-051 passive-righting campaign. The independent challenge admits qualified post-abort limp recovery; this does not impose passive righting on every candidate architecture."; }
    metadata basisCapsizeGateProgressRetention : Basis about BlueDogRequirements::CapsizeGateProgressRetention { kind = Kind::selectedStrategy; rationale = "Acceptance belongs to the selected N-051 passive-righting campaign. The independent challenge admits qualified post-abort limp recovery; this does not impose passive righting on every candidate architecture."; }
    metadata basisCapsizeQualificationRetention : Basis about BlueDogRequirements::CapsizeQualificationRetention { kind = Kind::selectedStrategy; rationale = "Acceptance belongs to the selected N-051 passive-righting campaign. The independent challenge admits qualified post-abort limp recovery; this does not impose passive righting on every candidate architecture."; }
    metadata basisCapsizeRestrictionRetention : Basis about BlueDogRequirements::CapsizeRestrictionRetention { kind = Kind::selectedStrategy; rationale = "Acceptance belongs to the selected N-051 passive-righting campaign. The independent challenge admits qualified post-abort limp recovery; this does not impose passive righting on every candidate architecture."; }
    metadata basisEnergyEvidenceReadiness : Basis about BlueDogRequirements::EnergyEvidenceReadiness { kind = Kind::assuranceObligation; rationale = "This constrains the evidence or assessment process. A completed analysis or reviewed statement is distinct from installed-vessel physical qualification."; }
    metadata basisRegulatoryClassification : Basis about BlueDogRequirements::RegulatoryClassification { kind = Kind::assuranceObligation; rationale = "This constrains the evidence or assessment process. A completed analysis or reviewed statement is distinct from installed-vessel physical qualification."; }
    metadata basisReliabilityEvidence : Basis about BlueDogRequirements::ReliabilityEvidence { kind = Kind::assuranceObligation; rationale = "This constrains the evidence or assessment process. A completed analysis or reviewed statement is distinct from installed-vessel physical qualification."; }
    metadata basisCruiseEvidence : Basis about BlueDogRequirements::CruiseEvidence { kind = Kind::assuranceObligation; rationale = "This constrains the evidence or assessment process. A completed analysis or reviewed statement is distinct from installed-vessel physical qualification."; }
    metadata basisLegProgress : Basis about BlueDogRequirements::LegProgress { kind = Kind::assuranceObligation; rationale = "This constrains the evidence or assessment process. A completed analysis or reviewed statement is distinct from installed-vessel physical qualification."; }
    metadata basisEnergyEstimateCadence : Basis about BlueDogRequirements::EnergyEstimateCadence { kind = Kind::performanceAllocation; rationale = "Retained baseline acceptance allocation under its stated campaign and mode conditions. The numerical limit is not uniquely implied by mission success; justify it through control, encounter, environmental or handling evidence before design release."; }
    metadata basisReserveEstimateCadence : Basis about BlueDogRequirements::ReserveEstimateCadence { kind = Kind::performanceAllocation; rationale = "Retained baseline acceptance allocation under its stated campaign and mode conditions. The numerical limit is not uniquely implied by mission success; justify it through control, encounter, environmental or handling evidence before design release."; }
    metadata basisEnergyEstimateAccuracy : Basis about BlueDogRequirements::EnergyEstimateAccuracy { kind = Kind::performanceAllocation; rationale = "Retained baseline acceptance allocation under its stated campaign and mode conditions. The numerical limit is not uniquely implied by mission success; justify it through control, encounter, environmental or handling evidence before design release."; }
    metadata basisGuidanceUpdateCadence : Basis about BlueDogRequirements::GuidanceUpdateCadence { kind = Kind::performanceAllocation; rationale = "Retained baseline acceptance allocation under its stated campaign and mode conditions. The numerical limit is not uniquely implied by mission success; justify it through control, encounter, environmental or handling evidence before design release."; }
    metadata basisSailCommandCadence : Basis about BlueDogRequirements::SailCommandCadence { kind = Kind::performanceAllocation; rationale = "Retained baseline acceptance allocation under its stated campaign and mode conditions. The numerical limit is not uniquely implied by mission success; justify it through control, encounter, environmental or handling evidence before design release."; }
    metadata basisSteeringCommandCadence : Basis about BlueDogRequirements::SteeringCommandCadence { kind = Kind::performanceAllocation; rationale = "Retained baseline acceptance allocation under its stated campaign and mode conditions. The numerical limit is not uniquely implied by mission success; justify it through control, encounter, environmental or handling evidence before design release."; }
    metadata basisRestartDeadline : Basis about BlueDogRequirements::RestartDeadline { kind = Kind::performanceAllocation; rationale = "Retained baseline acceptance allocation under its stated campaign and mode conditions. The numerical limit is not uniquely implied by mission success; justify it through control, encounter, environmental or handling evidence before design release."; }
    metadata basisLowEnergyEntry : Basis about BlueDogRequirements::LowEnergyEntry { kind = Kind::performanceAllocation; rationale = "Retained baseline acceptance allocation under its stated campaign and mode conditions. The numerical limit is not uniquely implied by mission success; justify it through control, encounter, environmental or handling evidence before design release."; }
    metadata basisLowEnergyExit : Basis about BlueDogRequirements::LowEnergyExit { kind = Kind::performanceAllocation; rationale = "Retained baseline acceptance allocation under its stated campaign and mode conditions. The numerical limit is not uniquely implied by mission success; justify it through control, encounter, environmental or handling evidence before design release."; }
    metadata basisTelemetryDeliveryCadence : Basis about BlueDogRequirements::TelemetryDeliveryCadence { kind = Kind::performanceAllocation; rationale = "Retained baseline acceptance allocation under its stated campaign and mode conditions. The numerical limit is not uniquely implied by mission success; justify it through control, encounter, environmental or handling evidence before design release."; }
    metadata basisOutageAutonomy : Basis about BlueDogRequirements::OutageAutonomy { kind = Kind::performanceAllocation; rationale = "Retained baseline acceptance allocation under its stated campaign and mode conditions. The numerical limit is not uniquely implied by mission success; justify it through control, encounter, environmental or handling evidence before design release."; }
    metadata basisIngressDetection : Basis about BlueDogRequirements::IngressDetection { kind = Kind::performanceAllocation; rationale = "Retained baseline acceptance allocation under its stated campaign and mode conditions. The numerical limit is not uniquely implied by mission success; justify it through control, encounter, environmental or handling evidence before design release."; }
    metadata basisPeriodicLogCadence : Basis about BlueDogRequirements::PeriodicLogCadence { kind = Kind::performanceAllocation; rationale = "Retained baseline acceptance allocation under its stated campaign and mode conditions. The numerical limit is not uniquely implied by mission success; justify it through control, encounter, environmental or handling evidence before design release."; }
    metadata basisLogRetention : Basis about BlueDogRequirements::LogRetention { kind = Kind::performanceAllocation; rationale = "Retained baseline acceptance allocation under its stated campaign and mode conditions. The numerical limit is not uniquely implied by mission success; justify it through control, encounter, environmental or handling evidence before design release."; }
    metadata basisLogTimestampAccuracy : Basis about BlueDogRequirements::LogTimestampAccuracy { kind = Kind::performanceAllocation; rationale = "Retained baseline acceptance allocation under its stated campaign and mode conditions. The numerical limit is not uniquely implied by mission success; justify it through control, encounter, environmental or handling evidence before design release."; }
    metadata basisLogInterruptionDurability : Basis about BlueDogRequirements::LogInterruptionDurability { kind = Kind::performanceAllocation; rationale = "Retained baseline acceptance allocation under its stated campaign and mode conditions. The numerical limit is not uniquely implied by mission success; justify it through control, encounter, environmental or handling evidence before design release."; }
    metadata basisNavigationValidEpochs : Basis about BlueDogRequirements::NavigationValidEpochs { kind = Kind::performanceAllocation; rationale = "Retained baseline acceptance allocation under its stated campaign and mode conditions. The numerical limit is not uniquely implied by mission success; justify it through control, encounter, environmental or handling evidence before design release."; }
    metadata basisStaleNavigationInvalidation : Basis about BlueDogRequirements::StaleNavigationInvalidation { kind = Kind::performanceAllocation; rationale = "Retained baseline acceptance allocation under its stated campaign and mode conditions. The numerical limit is not uniquely implied by mission success; justify it through control, encounter, environmental or handling evidence before design release."; }
    metadata basisNavigationDegradedTransition : Basis about BlueDogRequirements::NavigationDegradedTransition { kind = Kind::performanceAllocation; rationale = "Retained baseline acceptance allocation under its stated campaign and mode conditions. The numerical limit is not uniquely implied by mission success; justify it through control, encounter, environmental or handling evidence before design release."; }
    metadata basisReplacementDuration : Basis about BlueDogRequirements::ReplacementDuration { kind = Kind::performanceAllocation; rationale = "Retained baseline acceptance allocation under its stated campaign and mode conditions. The numerical limit is not uniquely implied by mission success; justify it through control, encounter, environmental or handling evidence before design release."; }
    metadata basisSoloTransport : Basis about BlueDogRequirements::SoloTransport { kind = Kind::performanceAllocation; rationale = "Retained baseline acceptance allocation under its stated campaign and mode conditions. The numerical limit is not uniquely implied by mission success; justify it through control, encounter, environmental or handling evidence before design release."; }
    metadata basisCollisionAssessmentCadence : Basis about BlueDogRequirements::CollisionAssessmentCadence { kind = Kind::performanceAllocation; rationale = "Retained baseline acceptance allocation under its stated campaign and mode conditions. The numerical limit is not uniquely implied by mission success; justify it through control, encounter, environmental or handling evidence before design release."; }
    metadata basisAvoidanceCommandDeadline : Basis about BlueDogRequirements::AvoidanceCommandDeadline { kind = Kind::performanceAllocation; rationale = "Retained baseline acceptance allocation under its stated campaign and mode conditions. The numerical limit is not uniquely implied by mission success; justify it through control, encounter, environmental or handling evidence before design release."; }
    metadata basisTrafficAwarenessFault : Basis about BlueDogRequirements::TrafficAwarenessFault { kind = Kind::performanceAllocation; rationale = "Retained baseline acceptance allocation under its stated campaign and mode conditions. The numerical limit is not uniquely implied by mission success; justify it through control, encounter, environmental or handling evidence before design release."; }
    metadata basisBoundaryEvaluationCadence : Basis about BlueDogRequirements::BoundaryEvaluationCadence { kind = Kind::performanceAllocation; rationale = "Retained baseline acceptance allocation under its stated campaign and mode conditions. The numerical limit is not uniquely implied by mission success; justify it through control, encounter, environmental or handling evidence before design release."; }
    metadata basisBoundaryAvoidanceDeadline : Basis about BlueDogRequirements::BoundaryAvoidanceDeadline { kind = Kind::performanceAllocation; rationale = "Retained baseline acceptance allocation under its stated campaign and mode conditions. The numerical limit is not uniquely implied by mission success; justify it through control, encounter, environmental or handling evidence before design release."; }
    metadata basisAbortLatchDeadline : Basis about BlueDogRequirements::AbortLatchDeadline { kind = Kind::performanceAllocation; rationale = "Retained baseline acceptance allocation under its stated campaign and mode conditions. The numerical limit is not uniquely implied by mission success; justify it through control, encounter, environmental or handling evidence before design release."; }
    metadata basisRecoveryTelemetryCadence : Basis about BlueDogRequirements::RecoveryTelemetryCadence { kind = Kind::performanceAllocation; rationale = "Retained baseline acceptance allocation under its stated campaign and mode conditions. The numerical limit is not uniquely implied by mission success; justify it through control, encounter, environmental or handling evidence before design release."; }
    metadata basisMotorIsolationDeadline : Basis about BlueDogRequirements::MotorIsolationDeadline { kind = Kind::performanceAllocation; rationale = "Retained baseline acceptance allocation under its stated campaign and mode conditions. The numerical limit is not uniquely implied by mission success; justify it through control, encounter, environmental or handling evidence before design release."; }
    metadata basisManualControlLossShutdown : Basis about BlueDogRequirements::ManualControlLossShutdown { kind = Kind::performanceAllocation; rationale = "Retained baseline acceptance allocation under its stated campaign and mode conditions. The numerical limit is not uniquely implied by mission success; justify it through control, encounter, environmental or handling evidence before design release."; }
    metadata basisSignalingModeDeadline : Basis about BlueDogRequirements::SignalingModeDeadline { kind = Kind::performanceAllocation; rationale = "Retained baseline acceptance allocation under its stated campaign and mode conditions. The numerical limit is not uniquely implied by mission success; justify it through control, encounter, environmental or handling evidence before design release."; }
    metadata basisSignalingFaultRecording : Basis about BlueDogRequirements::SignalingFaultRecording { kind = Kind::performanceAllocation; rationale = "Retained baseline acceptance allocation under its stated campaign and mode conditions. The numerical limit is not uniquely implied by mission success; justify it through control, encounter, environmental or handling evidence before design release."; }
    metadata basisSignalingFaultReporting : Basis about BlueDogRequirements::SignalingFaultReporting { kind = Kind::performanceAllocation; rationale = "Retained baseline acceptance allocation under its stated campaign and mode conditions. The numerical limit is not uniquely implied by mission success; justify it through control, encounter, environmental or handling evidence before design release."; }
    metadata basisExpiredCommandRejection : Basis about BlueDogRequirements::ExpiredCommandRejection { kind = Kind::performanceAllocation; rationale = "Retained baseline acceptance allocation under its stated campaign and mode conditions. The numerical limit is not uniquely implied by mission success; justify it through control, encounter, environmental or handling evidence before design release."; }
    metadata basisAcceptedCommandDeadline : Basis about BlueDogRequirements::AcceptedCommandDeadline { kind = Kind::performanceAllocation; rationale = "Retained baseline acceptance allocation under its stated campaign and mode conditions. The numerical limit is not uniquely implied by mission success; justify it through control, encounter, environmental or handling evidence before design release."; }
    metadata basisOnboardAcknowledgmentDeadline : Basis about BlueDogRequirements::OnboardAcknowledgmentDeadline { kind = Kind::performanceAllocation; rationale = "Retained baseline acceptance allocation under its stated campaign and mode conditions. The numerical limit is not uniquely implied by mission success; justify it through control, encounter, environmental or handling evidence before design release."; }
    metadata basisGorgeWind : Basis about BlueDogRequirements::GorgeWind { kind = Kind::performanceAllocation; rationale = "Retained baseline acceptance allocation under its stated campaign and mode conditions. The numerical limit is not uniquely implied by mission success; justify it through control, encounter, environmental or handling evidence before design release."; }
    metadata basisGorgeWaves : Basis about BlueDogRequirements::GorgeWaves { kind = Kind::performanceAllocation; rationale = "Retained baseline acceptance allocation under its stated campaign and mode conditions. The numerical limit is not uniquely implied by mission success; justify it through control, encounter, environmental or handling evidence before design release."; }
    metadata basisGorgeCurrent : Basis about BlueDogRequirements::GorgeCurrent { kind = Kind::performanceAllocation; rationale = "Retained baseline acceptance allocation under its stated campaign and mode conditions. The numerical limit is not uniquely implied by mission success; justify it through control, encounter, environmental or handling evidence before design release."; }
    metadata basisGorgeSurvivalWind : Basis about BlueDogRequirements::GorgeSurvivalWind { kind = Kind::performanceAllocation; rationale = "Retained baseline acceptance allocation under its stated campaign and mode conditions. The numerical limit is not uniquely implied by mission success; justify it through control, encounter, environmental or handling evidence before design release."; }
    metadata basisGorgeSurvivalWaves : Basis about BlueDogRequirements::GorgeSurvivalWaves { kind = Kind::performanceAllocation; rationale = "Retained baseline acceptance allocation under its stated campaign and mode conditions. The numerical limit is not uniquely implied by mission success; justify it through control, encounter, environmental or handling evidence before design release."; }
    metadata basisAirTemperature : Basis about BlueDogRequirements::AirTemperature { kind = Kind::performanceAllocation; rationale = "Retained baseline acceptance allocation under its stated campaign and mode conditions. The numerical limit is not uniquely implied by mission success; justify it through control, encounter, environmental or handling evidence before design release."; }
    metadata basisWaterTemperature : Basis about BlueDogRequirements::WaterTemperature { kind = Kind::performanceAllocation; rationale = "Retained baseline acceptance allocation under its stated campaign and mode conditions. The numerical limit is not uniquely implied by mission success; justify it through control, encounter, environmental or handling evidence before design release."; }
    metadata basisHumidity : Basis about BlueDogRequirements::Humidity { kind = Kind::performanceAllocation; rationale = "Retained baseline acceptance allocation under its stated campaign and mode conditions. The numerical limit is not uniquely implied by mission success; justify it through control, encounter, environmental or handling evidence before design release."; }
    metadata basisVisibility : Basis about BlueDogRequirements::Visibility { kind = Kind::performanceAllocation; rationale = "Retained baseline acceptance allocation under its stated campaign and mode conditions. The numerical limit is not uniquely implied by mission success; justify it through control, encounter, environmental or handling evidence before design release."; }
    metadata basisCalmOperation : Basis about BlueDogRequirements::CalmOperation { kind = Kind::performanceAllocation; rationale = "Retained baseline acceptance allocation under its stated campaign and mode conditions. The numerical limit is not uniquely implied by mission success; justify it through control, encounter, environmental or handling evidence before design release."; }
    metadata basisEnvelopeTransition : Basis about BlueDogRequirements::EnvelopeTransition { kind = Kind::performanceAllocation; rationale = "Retained baseline acceptance allocation under its stated campaign and mode conditions. The numerical limit is not uniquely implied by mission success; justify it through control, encounter, environmental or handling evidence before design release."; }
    metadata basisEnclosureSealing : Basis about BlueDogRequirements::EnclosureSealing { kind = Kind::performanceAllocation; rationale = "Retained baseline acceptance allocation under its stated campaign and mode conditions. The numerical limit is not uniquely implied by mission success; justify it through control, encounter, environmental or handling evidence before design release."; }
    metadata basisSolarHeating : Basis about BlueDogRequirements::SolarHeating { kind = Kind::performanceAllocation; rationale = "Retained baseline acceptance allocation under its stated campaign and mode conditions. The numerical limit is not uniquely implied by mission success; justify it through control, encounter, environmental or handling evidence before design release."; }
    metadata basisSubmergedWeedPassage : Basis about BlueDogRequirements::SubmergedWeedPassage { kind = Kind::performanceAllocation; rationale = "Retained baseline acceptance allocation under its stated campaign and mode conditions. The numerical limit is not uniquely implied by mission success; justify it through control, encounter, environmental or handling evidence before design release."; }
    metadata basisWeedSnagShedding : Basis about BlueDogRequirements::WeedSnagShedding { kind = Kind::performanceAllocation; rationale = "Retained baseline acceptance allocation under its stated campaign and mode conditions. The numerical limit is not uniquely implied by mission success; justify it through control, encounter, environmental or handling evidence before design release."; }
    metadata basisWeedBlockageResponse : Basis about BlueDogRequirements::WeedBlockageResponse { kind = Kind::performanceAllocation; rationale = "Retained baseline acceptance allocation under its stated campaign and mode conditions. The numerical limit is not uniquely implied by mission success; justify it through control, encounter, environmental or handling evidence before design release."; }
    metadata basisRecoveryPropulsorWeeds : Basis about BlueDogRequirements::RecoveryPropulsorWeeds { kind = Kind::performanceAllocation; rationale = "Retained baseline acceptance allocation under its stated campaign and mode conditions. The numerical limit is not uniquely implied by mission success; justify it through control, encounter, environmental or handling evidence before design release."; }
    metadata basisRestrictedVisibilityEntry : Basis about BlueDogRequirements::RestrictedVisibilityEntry { kind = Kind::performanceAllocation; rationale = "Retained baseline acceptance allocation under its stated campaign and mode conditions. The numerical limit is not uniquely implied by mission success; justify it through control, encounter, environmental or handling evidence before design release."; }
    metadata basisSurvivalEntryDeadline : Basis about BlueDogRequirements::SurvivalEntryDeadline { kind = Kind::performanceAllocation; rationale = "Retained baseline acceptance allocation under its stated campaign and mode conditions. The numerical limit is not uniquely implied by mission success; justify it through control, encounter, environmental or handling evidence before design release."; }
    metadata basisSailingResumptionDeadline : Basis about BlueDogRequirements::SailingResumptionDeadline { kind = Kind::performanceAllocation; rationale = "Retained baseline acceptance allocation under its stated campaign and mode conditions. The numerical limit is not uniquely implied by mission success; justify it through control, encounter, environmental or handling evidence before design release."; }
    metadata basisWetConductorResistance : Basis about BlueDogRequirements::WetConductorResistance { kind = Kind::performanceAllocation; rationale = "Retained baseline acceptance allocation under its stated campaign and mode conditions. The numerical limit is not uniquely implied by mission success; justify it through control, encounter, environmental or handling evidence before design release."; }
    metadata basisWetInsulationResistance : Basis about BlueDogRequirements::WetInsulationResistance { kind = Kind::performanceAllocation; rationale = "Retained baseline acceptance allocation under its stated campaign and mode conditions. The numerical limit is not uniquely implied by mission success; justify it through control, encounter, environmental or handling evidence before design release."; }
    metadata basisWeedPassageSpeed : Basis about BlueDogRequirements::WeedPassageSpeed { kind = Kind::performanceAllocation; rationale = "Retained baseline acceptance allocation under its stated campaign and mode conditions. The numerical limit is not uniquely implied by mission success; justify it through control, encounter, environmental or handling evidence before design release."; }
    metadata basisWeedPassageSteering : Basis about BlueDogRequirements::WeedPassageSteering { kind = Kind::performanceAllocation; rationale = "Retained baseline acceptance allocation under its stated campaign and mode conditions. The numerical limit is not uniquely implied by mission success; justify it through control, encounter, environmental or handling evidence before design release."; }
    metadata basisWeedSnagSpeedRecovery : Basis about BlueDogRequirements::WeedSnagSpeedRecovery { kind = Kind::performanceAllocation; rationale = "Retained baseline acceptance allocation under its stated campaign and mode conditions. The numerical limit is not uniquely implied by mission success; justify it through control, encounter, environmental or handling evidence before design release."; }
    metadata basisWeedSnagSteeringRecovery : Basis about BlueDogRequirements::WeedSnagSteeringRecovery { kind = Kind::performanceAllocation; rationale = "Retained baseline acceptance allocation under its stated campaign and mode conditions. The numerical limit is not uniquely implied by mission success; justify it through control, encounter, environmental or handling evidence before design release."; }
    metadata basisWeedBlockageFault : Basis about BlueDogRequirements::WeedBlockageFault { kind = Kind::performanceAllocation; rationale = "Retained baseline acceptance allocation under its stated campaign and mode conditions. The numerical limit is not uniquely implied by mission success; justify it through control, encounter, environmental or handling evidence before design release."; }
    metadata basisWeedBlockageContingency : Basis about BlueDogRequirements::WeedBlockageContingency { kind = Kind::performanceAllocation; rationale = "Retained baseline acceptance allocation under its stated campaign and mode conditions. The numerical limit is not uniquely implied by mission success; justify it through control, encounter, environmental or handling evidence before design release."; }
    metadata basisPoweredWeedSpeed : Basis about BlueDogRequirements::PoweredWeedSpeed { kind = Kind::performanceAllocation; rationale = "Retained baseline acceptance allocation under its stated campaign and mode conditions. The numerical limit is not uniquely implied by mission success; justify it through control, encounter, environmental or handling evidence before design release."; }
    metadata basisLockedPropulsorShutdown : Basis about BlueDogRequirements::LockedPropulsorShutdown { kind = Kind::performanceAllocation; rationale = "Retained baseline acceptance allocation under its stated campaign and mode conditions. The numerical limit is not uniquely implied by mission success; justify it through control, encounter, environmental or handling evidence before design release."; }
    metadata basisWindStaleInvalidation : Basis about BlueDogRequirements::WindStaleInvalidation { kind = Kind::performanceAllocation; rationale = "Retained baseline acceptance allocation under its stated campaign and mode conditions. The numerical limit is not uniquely implied by mission success; justify it through control, encounter, environmental or handling evidence before design release."; }
    metadata basisWindLossResponse : Basis about BlueDogRequirements::WindLossResponse { kind = Kind::performanceAllocation; rationale = "Retained baseline acceptance allocation under its stated campaign and mode conditions. The numerical limit is not uniquely implied by mission success; justify it through control, encounter, environmental or handling evidence before design release."; }
    metadata def ProcessObligation {
        attribute responsibleRole : String;
        attribute output : String;
        attribute acceptance : String;
    }
    metadata def AllocationDecision {
        attribute source : String;
        attribute applicability : String;
        attribute valueJustification : String;
        attribute marginBasis : String;
        attribute evidenceNeeded : String;
        attribute owner : String;
        attribute closureAction : String;
        attribute accepted : Boolean;
    }

    metadata processRegulatoryClassification : ProcessObligation about BlueDogRequirements::RegulatoryClassification {
        responsibleRole = "Project owner"; output = "Deployment compliance assessment"; acceptance = "Configuration-specific applicable navigation, radio and authorization evidence reviewed before deployment.";
    }
    metadata processDeploymentComplianceRecord : ProcessObligation about BlueDogRequirements::DeploymentComplianceRecord {
        responsibleRole = "Project owner"; output = "Deployment compliance record"; acceptance = "Identify the governing matrix, evidence, authority and unresolved exclusions.";
    }
    metadata processDeploymentReleaseGate : ProcessObligation about BlueDogRequirements::DeploymentReleaseGate {
        responsibleRole = "Project owner"; output = "Deployment release decision"; acceptance = "Reject unresolved applicable compliance obligations.";
    }
    metadata processLegProgress : ProcessObligation about BlueDogRequirements::LegProgress {
        responsibleRole = "Project owner, mission assessment"; output = "Reproducible whole-route scenario assessment"; acceptance = "Include sailing legs, holds, maneuvers and failed routes; no fixed speed floor.";
    }
    metadata processCruiseEvidence : ProcessObligation about BlueDogRequirements::CruiseEvidence {
        responsibleRole = "Project owner, mission assessment"; output = "Configuration-specific mission performance evidence"; acceptance = "Review route ensemble coverage and installed validity; calculations alone do not accept evidence.";
    }
    metadata processReliabilityEvidence : ProcessObligation about BlueDogRequirements::ReliabilityEvidence {
        responsibleRole = "Project owner, reliability assessment"; output = "Reliability evidence argument"; acceptance = "Review mission-critical functions, exposure, rates, dependence and evidence applicability independently of provisional targets.";
    }
    metadata processCriticalFailureDisposition : ProcessObligation about BlueDogRequirements::CriticalFailureDisposition {
        responsibleRole = "Project owner, safety assessment"; output = "Failure dispositions"; acceptance = "Resolve applicable critical failure and common-cause actions before release.";
    }
    metadata processEnergyEvidenceReadiness : ProcessObligation about BlueDogRequirements::EnergyEvidenceReadiness {
        responsibleRole = "Project owner, energy assessment"; output = "Energy-case acceptance record"; acceptance = "Identify accepted installed loads, resource bounds, battery derating and interval resolution evidence.";
    }
    metadata processNavigationRuleApplicability : ProcessObligation about GorgeChallenge::NavigationRuleApplicability {
        responsibleRole = "Entrant"; output = "NavigationRuleApplicability record for the identified configuration and attempt"; acceptance = "Review the requirement conditions using the entry/adjudication verification case; no accepted evidence is implied by this role assignment.";
    }
    metadata processNavigationRuleBaseline : ProcessObligation about GorgeChallenge::NavigationRuleBaseline {
        responsibleRole = "Organizer"; output = "NavigationRuleBaseline record for the identified configuration and attempt"; acceptance = "Review the requirement conditions using the entry/adjudication verification case; no accepted evidence is implied by this role assignment.";
    }
    metadata processNavigationEntryEvidence : ProcessObligation about GorgeChallenge::NavigationEntryEvidence {
        responsibleRole = "Organizer"; output = "NavigationEntryEvidence record for the identified configuration and attempt"; acceptance = "Review the requirement conditions using the entry/adjudication verification case; no accepted evidence is implied by this role assignment.";
    }
    metadata processOperatorSafetyIntervention : ProcessObligation about GorgeChallenge::OperatorSafetyIntervention {
        responsibleRole = "Operator"; output = "OperatorSafetyIntervention record for the identified configuration and attempt"; acceptance = "Review the requirement conditions using the entry/adjudication verification case; no accepted evidence is implied by this role assignment.";
    }
    metadata processNavigationAdjudication : ProcessObligation about GorgeChallenge::NavigationAdjudication {
        responsibleRole = "Organizer"; output = "NavigationAdjudication record for the identified configuration and attempt"; acceptance = "Review the requirement conditions using the entry/adjudication verification case; no accepted evidence is implied by this role assignment.";
    }

    metadata decisionLiftMass : AllocationDecision about BlueDogRequirements::LiftMass {
        source = "Retained baseline P-102; BlueDogRequirementBasis::basis16 records its provisional allocation. No accepted originating value-selection trade is recorded.";
        applicability = "P-102 retains its own normative conditions and mission applicability: current/shared; selected configuration and conditions govern.";
        valueJustification = "Open: justify the actual limit in P-102 LiftMass; mission motivation alone does not select that value.";
        marginBasis = "Open: record measurement uncertainty, variability and margin for P-102; no extra numerical margin is allocated by this decision record.";
        evidenceNeeded = "BlueDogRequirementVerification::TransportabilityVerification; accepted configuration-specific measurements and the value-selection argument remain required.";
        owner = "Project owner; supporting assessment responsibility follows the named verification case.";
        closureAction = "Before release of P-102: Measure timed handling tasks, carried loads and setup interfaces with one adult and permitted aids; compare the selected limit with repeatability, fatigue and launch/retrieval conditions. Record the retained or revised value, alternatives, evidence references, assumptions and acceptance disposition.";
        accepted = false;
    }
    metadata decisionSetupDuration : AllocationDecision about BlueDogRequirements::SetupDuration {
        source = "Retained baseline P-103; BlueDogRequirementBasis::basis17 records its provisional allocation. No accepted originating value-selection trade is recorded.";
        applicability = "P-103 retains its own normative conditions and mission applicability: current/shared; selected configuration and conditions govern.";
        valueJustification = "Open: justify the actual limit in P-103 SetupDuration; mission motivation alone does not select that value.";
        marginBasis = "Open: record measurement uncertainty, variability and margin for P-103; no extra numerical margin is allocated by this decision record.";
        evidenceNeeded = "BlueDogRequirementVerification::TransportabilityVerification; accepted configuration-specific measurements and the value-selection argument remain required.";
        owner = "Project owner; supporting assessment responsibility follows the named verification case.";
        closureAction = "Before release of P-103: Measure timed handling tasks, carried loads and setup interfaces with one adult and permitted aids; compare the selected limit with repeatability, fatigue and launch/retrieval conditions. Record the retained or revised value, alternatives, evidence references, assumptions and acceptance disposition.";
        accepted = false;
    }
    metadata decisionPackDuration : AllocationDecision about BlueDogRequirements::PackDuration {
        source = "Retained baseline P-104; BlueDogRequirementBasis::basis18 records its provisional allocation. No accepted originating value-selection trade is recorded.";
        applicability = "P-104 retains its own normative conditions and mission applicability: current/shared; selected configuration and conditions govern.";
        valueJustification = "Open: justify the actual limit in P-104 PackDuration; mission motivation alone does not select that value.";
        marginBasis = "Open: record measurement uncertainty, variability and margin for P-104; no extra numerical margin is allocated by this decision record.";
        evidenceNeeded = "BlueDogRequirementVerification::TransportabilityVerification; accepted configuration-specific measurements and the value-selection argument remain required.";
        owner = "Project owner; supporting assessment responsibility follows the named verification case.";
        closureAction = "Before release of P-104: Measure timed handling tasks, carried loads and setup interfaces with one adult and permitted aids; compare the selected limit with repeatability, fatigue and launch/retrieval conditions. Record the retained or revised value, alternatives, evidence references, assumptions and acceptance disposition.";
        accepted = false;
    }
    metadata decisionWindSampleCadence : AllocationDecision about BlueDogRequirements::WindSampleCadence {
        source = "Retained baseline E-146; BlueDogRequirementBasis::basis19 records its provisional allocation. No accepted originating value-selection trade is recorded.";
        applicability = "E-146 retains its own normative conditions and mission applicability: current/shared; selected configuration and conditions govern.";
        valueJustification = "Open: justify the actual limit in E-146 WindSampleCadence; mission motivation alone does not select that value.";
        marginBasis = "Open: record measurement uncertainty, variability and margin for E-146; no extra numerical margin is allocated by this decision record.";
        evidenceNeeded = "BlueDogRequirementVerification::WindObservationVerification; accepted configuration-specific measurements and the value-selection argument remain required.";
        owner = "Project owner; supporting assessment responsibility follows the named verification case.";
        closureAction = "Before release of E-146: Correlate the installed wind observation with a traceable reference across the declared flow/heel/trim matrix; reconcile local apparent-wind errors and the 10 m true-wind admission estimate before accepting the limit. Record the retained or revised value, alternatives, evidence references, assumptions and acceptance disposition.";
        accepted = false;
    }
    metadata decisionWindSpeedAccuracy : AllocationDecision about BlueDogRequirements::WindSpeedAccuracy {
        source = "Retained baseline E-147; BlueDogRequirementBasis::basis20 records its provisional allocation. No accepted originating value-selection trade is recorded.";
        applicability = "E-147 retains its own normative conditions and mission applicability: current/shared; selected configuration and conditions govern.";
        valueJustification = "Open: justify the actual limit in E-147 WindSpeedAccuracy; mission motivation alone does not select that value.";
        marginBasis = "Open: record measurement uncertainty, variability and margin for E-147; no extra numerical margin is allocated by this decision record.";
        evidenceNeeded = "BlueDogRequirementVerification::WindObservationVerification; accepted configuration-specific measurements and the value-selection argument remain required.";
        owner = "Project owner; supporting assessment responsibility follows the named verification case.";
        closureAction = "Before release of E-147: Correlate the installed wind observation with a traceable reference across the declared flow/heel/trim matrix; reconcile local apparent-wind errors and the 10 m true-wind admission estimate before accepting the limit. Record the retained or revised value, alternatives, evidence references, assumptions and acceptance disposition.";
        accepted = false;
    }
    metadata decisionWindDirectionAccuracy : AllocationDecision about BlueDogRequirements::WindDirectionAccuracy {
        source = "Retained baseline E-148; BlueDogRequirementBasis::basis21 records its provisional allocation. No accepted originating value-selection trade is recorded.";
        applicability = "E-148 retains its own normative conditions and mission applicability: current/shared; selected configuration and conditions govern.";
        valueJustification = "Open: justify the actual limit in E-148 WindDirectionAccuracy; mission motivation alone does not select that value.";
        marginBasis = "Open: record measurement uncertainty, variability and margin for E-148; no extra numerical margin is allocated by this decision record.";
        evidenceNeeded = "BlueDogRequirementVerification::WindObservationVerification; accepted configuration-specific measurements and the value-selection argument remain required.";
        owner = "Project owner; supporting assessment responsibility follows the named verification case.";
        closureAction = "Before release of E-148: Correlate the installed wind observation with a traceable reference across the declared flow/heel/trim matrix; reconcile local apparent-wind errors and the 10 m true-wind admission estimate before accepting the limit. Record the retained or revised value, alternatives, evidence references, assumptions and acceptance disposition.";
        accepted = false;
    }
    metadata decisionPositionAccuracy : AllocationDecision about BlueDogRequirements::PositionAccuracy {
        source = "Retained baseline E-108; BlueDogRequirementBasis::basis22 records its provisional allocation. No accepted originating value-selection trade is recorded.";
        applicability = "E-108 retains its own normative conditions and mission applicability: current/shared; selected configuration and conditions govern.";
        valueJustification = "Open: justify the actual limit in E-108 PositionAccuracy; mission motivation alone does not select that value.";
        marginBasis = "Open: record measurement uncertainty, variability and margin for E-108; no extra numerical margin is allocated by this decision record.";
        evidenceNeeded = "BlueDogRequirementVerification::NavigationAndControlVerification; accepted configuration-specific measurements and the value-selection argument remain required.";
        owner = "Project owner; supporting assessment responsibility follows the named verification case.";
        closureAction = "Before release of E-108: Measure installed command/observation refresh and fault-transition latency at the declared interface; compare the selected bound with achieved control response and interacting-fault safety margins. Record the retained or revised value, alternatives, evidence references, assumptions and acceptance disposition.";
        accepted = false;
    }
    metadata decisionHeadingAccuracy : AllocationDecision about BlueDogRequirements::HeadingAccuracy {
        source = "Retained baseline E-109; BlueDogRequirementBasis::basis23 records its provisional allocation. No accepted originating value-selection trade is recorded.";
        applicability = "E-109 retains its own normative conditions and mission applicability: current/shared; selected configuration and conditions govern.";
        valueJustification = "Open: justify the actual limit in E-109 HeadingAccuracy; mission motivation alone does not select that value.";
        marginBasis = "Open: record measurement uncertainty, variability and margin for E-109; no extra numerical margin is allocated by this decision record.";
        evidenceNeeded = "BlueDogRequirementVerification::NavigationAndControlVerification; accepted configuration-specific measurements and the value-selection argument remain required.";
        owner = "Project owner; supporting assessment responsibility follows the named verification case.";
        closureAction = "Before release of E-109: Measure installed command/observation refresh and fault-transition latency at the declared interface; compare the selected bound with achieved control response and interacting-fault safety margins. Record the retained or revised value, alternatives, evidence references, assumptions and acceptance disposition.";
        accepted = false;
    }
    metadata decisionRightingDeadline : AllocationDecision about BlueDogRequirements::RightingDeadline {
        source = "Retained baseline N-118; BlueDogRequirementBasis::basis24 records its provisional allocation. No accepted originating value-selection trade is recorded.";
        applicability = "N-118 retains its own normative conditions and mission applicability: current/shared; selected configuration and conditions govern.";
        valueJustification = "Open: justify the actual limit in N-118 RightingDeadline; mission motivation alone does not select that value.";
        marginBasis = "Open: record measurement uncertainty, variability and margin for N-118; no extra numerical margin is allocated by this decision record.";
        evidenceNeeded = "BlueDogRequirementVerification::SelfRightingVerification; accepted configuration-specific measurements and the value-selection argument remain required.";
        owner = "Project owner; supporting assessment responsibility follows the named verification case.";
        closureAction = "Before release of N-118: Establish representative site/casualty exposure and configuration-specific functional recovery; compare the selected boundary or response limit with measured failure margins and interacting exposures. Record the retained or revised value, alternatives, evidence references, assumptions and acceptance disposition.";
        accepted = false;
    }
    metadata decisionEnergyEstimateCadence : AllocationDecision about BlueDogRequirements::EnergyEstimateCadence {
        source = "Retained baseline E-101; BlueDogRequirementBasis::basisEnergyEstimateCadence records its provisional allocation. No accepted originating value-selection trade is recorded.";
        applicability = "E-101 retains its own normative conditions and mission applicability: current/shared; selected configuration and conditions govern.";
        valueJustification = "Open: justify the actual limit in E-101 EnergyEstimateCadence; mission motivation alone does not select that value.";
        marginBasis = "Open: record measurement uncertainty, variability and margin for E-101; no extra numerical margin is allocated by this decision record.";
        evidenceNeeded = "BlueDogRequirementVerification::EnergyAwarenessVerification; accepted configuration-specific measurements and the value-selection argument remain required.";
        owner = "Project owner; supporting assessment responsibility follows the named verification case.";
        closureAction = "Before release of E-101: Correlate installed energy estimates and reserve timing with calibrated withdrawal and temperature/aging evidence; compare the selected bound with route-dependent recovery margin. Record the retained or revised value, alternatives, evidence references, assumptions and acceptance disposition.";
        accepted = false;
    }
    metadata decisionReserveEstimateCadence : AllocationDecision about BlueDogRequirements::ReserveEstimateCadence {
        source = "Retained baseline E-102; BlueDogRequirementBasis::basisReserveEstimateCadence records its provisional allocation. No accepted originating value-selection trade is recorded.";
        applicability = "E-102 retains its own normative conditions and mission applicability: current/shared; selected configuration and conditions govern.";
        valueJustification = "Open: justify the actual limit in E-102 ReserveEstimateCadence; mission motivation alone does not select that value.";
        marginBasis = "Open: record measurement uncertainty, variability and margin for E-102; no extra numerical margin is allocated by this decision record.";
        evidenceNeeded = "BlueDogRequirementVerification::EnergyAwarenessVerification; accepted configuration-specific measurements and the value-selection argument remain required.";
        owner = "Project owner; supporting assessment responsibility follows the named verification case.";
        closureAction = "Before release of E-102: Correlate installed energy estimates and reserve timing with calibrated withdrawal and temperature/aging evidence; compare the selected bound with route-dependent recovery margin. Record the retained or revised value, alternatives, evidence references, assumptions and acceptance disposition.";
        accepted = false;
    }
    metadata decisionEnergyEstimateAccuracy : AllocationDecision about BlueDogRequirements::EnergyEstimateAccuracy {
        source = "Retained baseline E-103; BlueDogRequirementBasis::basisEnergyEstimateAccuracy records its provisional allocation. No accepted originating value-selection trade is recorded.";
        applicability = "E-103 retains its own normative conditions and mission applicability: current/shared; selected configuration and conditions govern.";
        valueJustification = "Open: justify the actual limit in E-103 EnergyEstimateAccuracy; mission motivation alone does not select that value.";
        marginBasis = "Open: record measurement uncertainty, variability and margin for E-103; no extra numerical margin is allocated by this decision record.";
        evidenceNeeded = "BlueDogRequirementVerification::EnergyAwarenessVerification; accepted configuration-specific measurements and the value-selection argument remain required.";
        owner = "Project owner; supporting assessment responsibility follows the named verification case.";
        closureAction = "Before release of E-103: Correlate installed energy estimates and reserve timing with calibrated withdrawal and temperature/aging evidence; compare the selected bound with route-dependent recovery margin. Record the retained or revised value, alternatives, evidence references, assumptions and acceptance disposition.";
        accepted = false;
    }
    metadata decisionGuidanceUpdateCadence : AllocationDecision about BlueDogRequirements::GuidanceUpdateCadence {
        source = "Retained baseline E-105; BlueDogRequirementBasis::basisGuidanceUpdateCadence records its provisional allocation. No accepted originating value-selection trade is recorded.";
        applicability = "E-105 retains its own normative conditions and mission applicability: current/shared; selected configuration and conditions govern.";
        valueJustification = "Open: justify the actual limit in E-105 GuidanceUpdateCadence; mission motivation alone does not select that value.";
        marginBasis = "Open: record measurement uncertainty, variability and margin for E-105; no extra numerical margin is allocated by this decision record.";
        evidenceNeeded = "BlueDogRequirementVerification::NavigationAndControlVerification; accepted configuration-specific measurements and the value-selection argument remain required.";
        owner = "Project owner; supporting assessment responsibility follows the named verification case.";
        closureAction = "Before release of E-105: Measure installed command/observation refresh and fault-transition latency at the declared interface; compare the selected bound with achieved control response and interacting-fault safety margins. Record the retained or revised value, alternatives, evidence references, assumptions and acceptance disposition.";
        accepted = false;
    }
    metadata decisionSailCommandCadence : AllocationDecision about BlueDogRequirements::SailCommandCadence {
        source = "Retained baseline E-106; BlueDogRequirementBasis::basisSailCommandCadence records its provisional allocation. No accepted originating value-selection trade is recorded.";
        applicability = "E-106 retains its own normative conditions and mission applicability: current/shared; selected configuration and conditions govern.";
        valueJustification = "Open: justify the actual limit in E-106 SailCommandCadence; mission motivation alone does not select that value.";
        marginBasis = "Open: record measurement uncertainty, variability and margin for E-106; no extra numerical margin is allocated by this decision record.";
        evidenceNeeded = "BlueDogRequirementVerification::NavigationAndControlVerification; accepted configuration-specific measurements and the value-selection argument remain required.";
        owner = "Project owner; supporting assessment responsibility follows the named verification case.";
        closureAction = "Before release of E-106: Measure installed command/observation refresh and fault-transition latency at the declared interface; compare the selected bound with achieved control response and interacting-fault safety margins. Record the retained or revised value, alternatives, evidence references, assumptions and acceptance disposition.";
        accepted = false;
    }
    metadata decisionSteeringCommandCadence : AllocationDecision about BlueDogRequirements::SteeringCommandCadence {
        source = "Retained baseline E-107; BlueDogRequirementBasis::basisSteeringCommandCadence records its provisional allocation. No accepted originating value-selection trade is recorded.";
        applicability = "E-107 retains its own normative conditions and mission applicability: current/shared; selected configuration and conditions govern.";
        valueJustification = "Open: justify the actual limit in E-107 SteeringCommandCadence; mission motivation alone does not select that value.";
        marginBasis = "Open: record measurement uncertainty, variability and margin for E-107; no extra numerical margin is allocated by this decision record.";
        evidenceNeeded = "BlueDogRequirementVerification::NavigationAndControlVerification; accepted configuration-specific measurements and the value-selection argument remain required.";
        owner = "Project owner; supporting assessment responsibility follows the named verification case.";
        closureAction = "Before release of E-107: Measure installed command/observation refresh and fault-transition latency at the declared interface; compare the selected bound with achieved control response and interacting-fault safety margins. Record the retained or revised value, alternatives, evidence references, assumptions and acceptance disposition.";
        accepted = false;
    }
    metadata decisionRestartDeadline : AllocationDecision about BlueDogRequirements::RestartDeadline {
        source = "Retained baseline E-110; BlueDogRequirementBasis::basisRestartDeadline records its provisional allocation. No accepted originating value-selection trade is recorded.";
        applicability = "E-110 retains its own normative conditions and mission applicability: current/shared; selected configuration and conditions govern.";
        valueJustification = "Open: justify the actual limit in E-110 RestartDeadline; mission motivation alone does not select that value.";
        marginBasis = "Open: record measurement uncertainty, variability and margin for E-110; no extra numerical margin is allocated by this decision record.";
        evidenceNeeded = "BlueDogRequirementVerification::ResetRecoveryVerification; accepted configuration-specific measurements and the value-selection argument remain required.";
        owner = "Project owner; supporting assessment responsibility follows the named verification case.";
        closureAction = "Before release of E-110: Measure installed command/observation refresh and fault-transition latency at the declared interface; compare the selected bound with achieved control response and interacting-fault safety margins. Record the retained or revised value, alternatives, evidence references, assumptions and acceptance disposition.";
        accepted = false;
    }
    metadata decisionLowEnergyEntry : AllocationDecision about BlueDogRequirements::LowEnergyEntry {
        source = "Retained baseline E-114; BlueDogRequirementBasis::basisLowEnergyEntry records its provisional allocation. No accepted originating value-selection trade is recorded.";
        applicability = "E-114 retains its own normative conditions and mission applicability: current/shared; selected configuration and conditions govern.";
        valueJustification = "Open: justify the actual limit in E-114 LowEnergyEntry; mission motivation alone does not select that value.";
        marginBasis = "Open: record measurement uncertainty, variability and margin for E-114; no extra numerical margin is allocated by this decision record.";
        evidenceNeeded = "BlueDogRequirementVerification::LowEnergyRecoveryVerification; accepted configuration-specific measurements and the value-selection argument remain required.";
        owner = "Project owner; supporting assessment responsibility follows the named verification case.";
        closureAction = "Before release of E-114: Correlate installed energy estimates and reserve timing with calibrated withdrawal and temperature/aging evidence; compare the selected bound with route-dependent recovery margin. Record the retained or revised value, alternatives, evidence references, assumptions and acceptance disposition.";
        accepted = false;
    }
    metadata decisionLowEnergyExit : AllocationDecision about BlueDogRequirements::LowEnergyExit {
        source = "Retained baseline E-118; BlueDogRequirementBasis::basisLowEnergyExit records its provisional allocation. No accepted originating value-selection trade is recorded.";
        applicability = "E-118 retains its own normative conditions and mission applicability: current/shared; selected configuration and conditions govern.";
        valueJustification = "Open: justify the actual limit in E-118 LowEnergyExit; mission motivation alone does not select that value.";
        marginBasis = "Open: record measurement uncertainty, variability and margin for E-118; no extra numerical margin is allocated by this decision record.";
        evidenceNeeded = "BlueDogRequirementVerification::LowEnergyRecoveryVerification; accepted configuration-specific measurements and the value-selection argument remain required.";
        owner = "Project owner; supporting assessment responsibility follows the named verification case.";
        closureAction = "Before release of E-118: Correlate installed energy estimates and reserve timing with calibrated withdrawal and temperature/aging evidence; compare the selected bound with route-dependent recovery margin. Record the retained or revised value, alternatives, evidence references, assumptions and acceptance disposition.";
        accepted = false;
    }
    metadata decisionTelemetryDeliveryCadence : AllocationDecision about BlueDogRequirements::TelemetryDeliveryCadence {
        source = "Retained baseline E-120; BlueDogRequirementBasis::basisTelemetryDeliveryCadence records its provisional allocation. No accepted originating value-selection trade is recorded.";
        applicability = "E-120 retains its own normative conditions and mission applicability: current/shared; selected configuration and conditions govern.";
        valueJustification = "Open: justify the actual limit in E-120 TelemetryDeliveryCadence; mission motivation alone does not select that value.";
        marginBasis = "Open: record measurement uncertainty, variability and margin for E-120; no extra numerical margin is allocated by this decision record.";
        evidenceNeeded = "BlueDogRequirementVerification::LowEnergyRecoveryVerification; BlueDogRequirementVerification::CommunicationsVerification; accepted configuration-specific measurements and the value-selection argument remain required.";
        owner = "Project owner; supporting assessment responsibility follows the named verification case.";
        closureAction = "Before release of E-120: Measure installed command/observation refresh and fault-transition latency at the declared interface; compare the selected bound with achieved control response and interacting-fault safety margins. Record the retained or revised value, alternatives, evidence references, assumptions and acceptance disposition.";
        accepted = false;
    }
    metadata decisionOutageAutonomy : AllocationDecision about BlueDogRequirements::OutageAutonomy {
        source = "Retained baseline E-121; BlueDogRequirementBasis::basisOutageAutonomy records its provisional allocation. No accepted originating value-selection trade is recorded.";
        applicability = "E-121 retains its own normative conditions and mission applicability: current/shared; selected configuration and conditions govern.";
        valueJustification = "Open: justify the actual limit in E-121 OutageAutonomy; mission motivation alone does not select that value.";
        marginBasis = "Open: record measurement uncertainty, variability and margin for E-121; no extra numerical margin is allocated by this decision record.";
        evidenceNeeded = "BlueDogRequirementVerification::CommunicationsVerification; accepted configuration-specific measurements and the value-selection argument remain required.";
        owner = "Project owner; supporting assessment responsibility follows the named verification case.";
        closureAction = "Before release of E-121: Measure installed command/observation refresh and fault-transition latency at the declared interface; compare the selected bound with achieved control response and interacting-fault safety margins. Record the retained or revised value, alternatives, evidence references, assumptions and acceptance disposition.";
        accepted = false;
    }
    metadata decisionIngressDetection : AllocationDecision about BlueDogRequirements::IngressDetection {
        source = "Retained baseline E-125; BlueDogRequirementBasis::basisIngressDetection records its provisional allocation. No accepted originating value-selection trade is recorded.";
        applicability = "E-125 retains its own normative conditions and mission applicability: current/shared; selected configuration and conditions govern.";
        valueJustification = "Open: justify the actual limit in E-125 IngressDetection; mission motivation alone does not select that value.";
        marginBasis = "Open: record measurement uncertainty, variability and margin for E-125; no extra numerical margin is allocated by this decision record.";
        evidenceNeeded = "BlueDogRequirementVerification::IngressResponseVerification; accepted configuration-specific measurements and the value-selection argument remain required.";
        owner = "Project owner; supporting assessment responsibility follows the named verification case.";
        closureAction = "Before release of E-125: Measure installed command/observation refresh and fault-transition latency at the declared interface; compare the selected bound with achieved control response and interacting-fault safety margins. Record the retained or revised value, alternatives, evidence references, assumptions and acceptance disposition.";
        accepted = false;
    }
    metadata decisionPeriodicLogCadence : AllocationDecision about BlueDogRequirements::PeriodicLogCadence {
        source = "Retained baseline E-130; BlueDogRequirementBasis::basisPeriodicLogCadence records its provisional allocation. No accepted originating value-selection trade is recorded.";
        applicability = "E-130 retains its own normative conditions and mission applicability: current/shared; selected configuration and conditions govern.";
        valueJustification = "Open: justify the actual limit in E-130 PeriodicLogCadence; mission motivation alone does not select that value.";
        marginBasis = "Open: record measurement uncertainty, variability and margin for E-130; no extra numerical margin is allocated by this decision record.";
        evidenceNeeded = "BlueDogRequirementVerification::LowEnergyRecoveryVerification; BlueDogRequirementVerification::MissionEvidenceVerification; BlueDogRequirementVerification::EmergencyControlVerification; BlueDogRequirementVerification::EnvelopeTransitionVerification; accepted configuration-specific measurements and the value-selection argument remain required.";
        owner = "Project owner; supporting assessment responsibility follows the named verification case.";
        closureAction = "Before release of E-130: Interrupt power, reset and communications at the recording boundaries; measure lost history, timestamp uncertainty and replay behavior against the selected bound. Record the retained or revised value, alternatives, evidence references, assumptions and acceptance disposition.";
        accepted = false;
    }
    metadata decisionLogRetention : AllocationDecision about BlueDogRequirements::LogRetention {
        source = "Retained baseline E-131; BlueDogRequirementBasis::basisLogRetention records its provisional allocation. No accepted originating value-selection trade is recorded.";
        applicability = "E-131 retains its own normative conditions and mission applicability: current/shared; selected configuration and conditions govern.";
        valueJustification = "Open: justify the actual limit in E-131 LogRetention; mission motivation alone does not select that value.";
        marginBasis = "Open: record measurement uncertainty, variability and margin for E-131; no extra numerical margin is allocated by this decision record.";
        evidenceNeeded = "BlueDogRequirementVerification::CommunicationsVerification; BlueDogRequirementVerification::MissionEvidenceVerification; accepted configuration-specific measurements and the value-selection argument remain required.";
        owner = "Project owner; supporting assessment responsibility follows the named verification case.";
        closureAction = "Before release of E-131: Interrupt power, reset and communications at the recording boundaries; measure lost history, timestamp uncertainty and replay behavior against the selected bound. Record the retained or revised value, alternatives, evidence references, assumptions and acceptance disposition.";
        accepted = false;
    }
    metadata decisionLogTimestampAccuracy : AllocationDecision about BlueDogRequirements::LogTimestampAccuracy {
        source = "Retained baseline E-133; BlueDogRequirementBasis::basisLogTimestampAccuracy records its provisional allocation. No accepted originating value-selection trade is recorded.";
        applicability = "E-133 retains its own normative conditions and mission applicability: current/shared; selected configuration and conditions govern.";
        valueJustification = "Open: justify the actual limit in E-133 LogTimestampAccuracy; mission motivation alone does not select that value.";
        marginBasis = "Open: record measurement uncertainty, variability and margin for E-133; no extra numerical margin is allocated by this decision record.";
        evidenceNeeded = "BlueDogRequirementVerification::MissionEvidenceVerification; accepted configuration-specific measurements and the value-selection argument remain required.";
        owner = "Project owner; supporting assessment responsibility follows the named verification case.";
        closureAction = "Before release of E-133: Interrupt power, reset and communications at the recording boundaries; measure lost history, timestamp uncertainty and replay behavior against the selected bound. Record the retained or revised value, alternatives, evidence references, assumptions and acceptance disposition.";
        accepted = false;
    }
    metadata decisionLogInterruptionDurability : AllocationDecision about BlueDogRequirements::LogInterruptionDurability {
        source = "Retained baseline E-136; BlueDogRequirementBasis::basisLogInterruptionDurability records its provisional allocation. No accepted originating value-selection trade is recorded.";
        applicability = "E-136 retains its own normative conditions and mission applicability: current/shared; selected configuration and conditions govern.";
        valueJustification = "Open: justify the actual limit in E-136 LogInterruptionDurability; mission motivation alone does not select that value.";
        marginBasis = "Open: record measurement uncertainty, variability and margin for E-136; no extra numerical margin is allocated by this decision record.";
        evidenceNeeded = "BlueDogRequirementVerification::ResetRecoveryVerification; BlueDogRequirementVerification::MissionEvidenceVerification; accepted configuration-specific measurements and the value-selection argument remain required.";
        owner = "Project owner; supporting assessment responsibility follows the named verification case.";
        closureAction = "Before release of E-136: Interrupt power, reset and communications at the recording boundaries; measure lost history, timestamp uncertainty and replay behavior against the selected bound. Record the retained or revised value, alternatives, evidence references, assumptions and acceptance disposition.";
        accepted = false;
    }
    metadata decisionNavigationValidEpochs : AllocationDecision about BlueDogRequirements::NavigationValidEpochs {
        source = "Retained baseline E-140; BlueDogRequirementBasis::basisNavigationValidEpochs records its provisional allocation. No accepted originating value-selection trade is recorded.";
        applicability = "E-140 retains its own normative conditions and mission applicability: current/shared; selected configuration and conditions govern.";
        valueJustification = "Open: justify the actual limit in E-140 NavigationValidEpochs; mission motivation alone does not select that value.";
        marginBasis = "Open: record measurement uncertainty, variability and margin for E-140; no extra numerical margin is allocated by this decision record.";
        evidenceNeeded = "BlueDogRequirementVerification::NavigationAvailabilityVerification; accepted configuration-specific measurements and the value-selection argument remain required.";
        owner = "Project owner; supporting assessment responsibility follows the named verification case.";
        closureAction = "Before release of E-140: Measure installed command/observation refresh and fault-transition latency at the declared interface; compare the selected bound with achieved control response and interacting-fault safety margins. Record the retained or revised value, alternatives, evidence references, assumptions and acceptance disposition.";
        accepted = false;
    }
    metadata decisionStaleNavigationInvalidation : AllocationDecision about BlueDogRequirements::StaleNavigationInvalidation {
        source = "Retained baseline E-141; BlueDogRequirementBasis::basisStaleNavigationInvalidation records its provisional allocation. No accepted originating value-selection trade is recorded.";
        applicability = "E-141 retains its own normative conditions and mission applicability: current/shared; selected configuration and conditions govern.";
        valueJustification = "Open: justify the actual limit in E-141 StaleNavigationInvalidation; mission motivation alone does not select that value.";
        marginBasis = "Open: record measurement uncertainty, variability and margin for E-141; no extra numerical margin is allocated by this decision record.";
        evidenceNeeded = "BlueDogRequirementVerification::NavigationAvailabilityVerification; accepted configuration-specific measurements and the value-selection argument remain required.";
        owner = "Project owner; supporting assessment responsibility follows the named verification case.";
        closureAction = "Before release of E-141: Measure installed command/observation refresh and fault-transition latency at the declared interface; compare the selected bound with achieved control response and interacting-fault safety margins. Record the retained or revised value, alternatives, evidence references, assumptions and acceptance disposition.";
        accepted = false;
    }
    metadata decisionNavigationDegradedTransition : AllocationDecision about BlueDogRequirements::NavigationDegradedTransition {
        source = "Retained baseline E-142; BlueDogRequirementBasis::basisNavigationDegradedTransition records its provisional allocation. No accepted originating value-selection trade is recorded.";
        applicability = "E-142 retains its own normative conditions and mission applicability: current/shared; selected configuration and conditions govern.";
        valueJustification = "Open: justify the actual limit in E-142 NavigationDegradedTransition; mission motivation alone does not select that value.";
        marginBasis = "Open: record measurement uncertainty, variability and margin for E-142; no extra numerical margin is allocated by this decision record.";
        evidenceNeeded = "BlueDogRequirementVerification::NavigationAvailabilityVerification; accepted configuration-specific measurements and the value-selection argument remain required.";
        owner = "Project owner; supporting assessment responsibility follows the named verification case.";
        closureAction = "Before release of E-142: Measure installed command/observation refresh and fault-transition latency at the declared interface; compare the selected bound with achieved control response and interacting-fault safety margins. Record the retained or revised value, alternatives, evidence references, assumptions and acceptance disposition.";
        accepted = false;
    }
    metadata decisionReplacementDuration : AllocationDecision about BlueDogRequirements::ReplacementDuration {
        source = "Retained baseline P-107; BlueDogRequirementBasis::basisReplacementDuration records its provisional allocation. No accepted originating value-selection trade is recorded.";
        applicability = "P-107 retains its own normative conditions and mission applicability: current/shared; selected configuration and conditions govern.";
        valueJustification = "Open: justify the actual limit in P-107 ReplacementDuration; mission motivation alone does not select that value.";
        marginBasis = "Open: record measurement uncertainty, variability and margin for P-107; no extra numerical margin is allocated by this decision record.";
        evidenceNeeded = "BlueDogRequirementVerification::ServiceabilityVerification; accepted configuration-specific measurements and the value-selection argument remain required.";
        owner = "Project owner; supporting assessment responsibility follows the named verification case.";
        closureAction = "Before release of P-107: Measure timed handling tasks, carried loads and setup interfaces with one adult and permitted aids; compare the selected limit with repeatability, fatigue and launch/retrieval conditions. Record the retained or revised value, alternatives, evidence references, assumptions and acceptance disposition.";
        accepted = false;
    }
    metadata decisionSoloTransport : AllocationDecision about BlueDogRequirements::SoloTransport {
        source = "Retained baseline P-101; BlueDogRequirementBasis::basisSoloTransport records its provisional allocation. No accepted originating value-selection trade is recorded.";
        applicability = "P-101 retains its own normative conditions and mission applicability: current/shared; selected configuration and conditions govern.";
        valueJustification = "Open: justify the actual limit in P-101 SoloTransport; mission motivation alone does not select that value.";
        marginBasis = "Open: record measurement uncertainty, variability and margin for P-101; no extra numerical margin is allocated by this decision record.";
        evidenceNeeded = "BlueDogRequirementVerification::TransportabilityVerification; accepted configuration-specific measurements and the value-selection argument remain required.";
        owner = "Project owner; supporting assessment responsibility follows the named verification case.";
        closureAction = "Before release of P-101: Measure timed handling tasks, carried loads and setup interfaces with one adult and permitted aids; compare the selected limit with repeatability, fatigue and launch/retrieval conditions. Record the retained or revised value, alternatives, evidence references, assumptions and acceptance disposition.";
        accepted = false;
    }
    metadata decisionCollisionAssessmentCadence : AllocationDecision about BlueDogRequirements::CollisionAssessmentCadence {
        source = "Retained baseline S-102; BlueDogRequirementBasis::basisCollisionAssessmentCadence records its provisional allocation. No accepted originating value-selection trade is recorded.";
        applicability = "S-102 retains its own normative conditions and mission applicability: current/shared; selected configuration and conditions govern.";
        valueJustification = "Open: justify the actual limit in S-102 CollisionAssessmentCadence; mission motivation alone does not select that value.";
        marginBasis = "Open: record measurement uncertainty, variability and margin for S-102; no extra numerical margin is allocated by this decision record.";
        evidenceNeeded = "BlueDogRequirementVerification::TrafficSafetyVerification; accepted configuration-specific measurements and the value-selection argument remain required.";
        owner = "Project owner; supporting assessment responsibility follows the named verification case.";
        closureAction = "Before release of S-102: Use installed observations and achieved maneuvers in representative and adverse encounters or emergency-control faults; compare the selected latency with complete response and safety margins. Record the retained or revised value, alternatives, evidence references, assumptions and acceptance disposition.";
        accepted = false;
    }
    metadata decisionAvoidanceCommandDeadline : AllocationDecision about BlueDogRequirements::AvoidanceCommandDeadline {
        source = "Retained baseline S-103; BlueDogRequirementBasis::basisAvoidanceCommandDeadline records its provisional allocation. No accepted originating value-selection trade is recorded.";
        applicability = "S-103 retains its own normative conditions and mission applicability: current/shared; selected configuration and conditions govern.";
        valueJustification = "Open: justify the actual limit in S-103 AvoidanceCommandDeadline; mission motivation alone does not select that value.";
        marginBasis = "Open: record measurement uncertainty, variability and margin for S-103; no extra numerical margin is allocated by this decision record.";
        evidenceNeeded = "BlueDogRequirementVerification::TrafficSafetyVerification; accepted configuration-specific measurements and the value-selection argument remain required.";
        owner = "Project owner; supporting assessment responsibility follows the named verification case.";
        closureAction = "Before release of S-103: Use installed observations and achieved maneuvers in representative and adverse encounters or emergency-control faults; compare the selected latency with complete response and safety margins. Record the retained or revised value, alternatives, evidence references, assumptions and acceptance disposition.";
        accepted = false;
    }
    metadata decisionTrafficAwarenessFault : AllocationDecision about BlueDogRequirements::TrafficAwarenessFault {
        source = "Retained baseline S-104; BlueDogRequirementBasis::basisTrafficAwarenessFault records its provisional allocation. No accepted originating value-selection trade is recorded.";
        applicability = "S-104 retains its own normative conditions and mission applicability: current/shared; selected configuration and conditions govern.";
        valueJustification = "Open: justify the actual limit in S-104 TrafficAwarenessFault; mission motivation alone does not select that value.";
        marginBasis = "Open: record measurement uncertainty, variability and margin for S-104; no extra numerical margin is allocated by this decision record.";
        evidenceNeeded = "BlueDogRequirementVerification::TrafficSafetyVerification; accepted configuration-specific measurements and the value-selection argument remain required.";
        owner = "Project owner; supporting assessment responsibility follows the named verification case.";
        closureAction = "Before release of S-104: Use installed observations and achieved maneuvers in representative and adverse encounters or emergency-control faults; compare the selected latency with complete response and safety margins. Record the retained or revised value, alternatives, evidence references, assumptions and acceptance disposition.";
        accepted = false;
    }
    metadata decisionBoundaryEvaluationCadence : AllocationDecision about BlueDogRequirements::BoundaryEvaluationCadence {
        source = "Retained baseline S-105; BlueDogRequirementBasis::basisBoundaryEvaluationCadence records its provisional allocation. No accepted originating value-selection trade is recorded.";
        applicability = "S-105 retains its own normative conditions and mission applicability: current/shared; selected configuration and conditions govern.";
        valueJustification = "Open: justify the actual limit in S-105 BoundaryEvaluationCadence; mission motivation alone does not select that value.";
        marginBasis = "Open: record measurement uncertainty, variability and margin for S-105; no extra numerical margin is allocated by this decision record.";
        evidenceNeeded = "BlueDogRequirementVerification::OperatingBoundaryVerification; accepted configuration-specific measurements and the value-selection argument remain required.";
        owner = "Project owner; supporting assessment responsibility follows the named verification case.";
        closureAction = "Before release of S-105: Use installed observations and achieved maneuvers in representative and adverse encounters or emergency-control faults; compare the selected latency with complete response and safety margins. Record the retained or revised value, alternatives, evidence references, assumptions and acceptance disposition.";
        accepted = false;
    }
    metadata decisionBoundaryAvoidanceDeadline : AllocationDecision about BlueDogRequirements::BoundaryAvoidanceDeadline {
        source = "Retained baseline S-106; BlueDogRequirementBasis::basisBoundaryAvoidanceDeadline records its provisional allocation. No accepted originating value-selection trade is recorded.";
        applicability = "S-106 retains its own normative conditions and mission applicability: current/shared; selected configuration and conditions govern.";
        valueJustification = "Open: justify the actual limit in S-106 BoundaryAvoidanceDeadline; mission motivation alone does not select that value.";
        marginBasis = "Open: record measurement uncertainty, variability and margin for S-106; no extra numerical margin is allocated by this decision record.";
        evidenceNeeded = "BlueDogRequirementVerification::OperatingBoundaryVerification; accepted configuration-specific measurements and the value-selection argument remain required.";
        owner = "Project owner; supporting assessment responsibility follows the named verification case.";
        closureAction = "Before release of S-106: Use installed observations and achieved maneuvers in representative and adverse encounters or emergency-control faults; compare the selected latency with complete response and safety margins. Record the retained or revised value, alternatives, evidence references, assumptions and acceptance disposition.";
        accepted = false;
    }
    metadata decisionAbortLatchDeadline : AllocationDecision about BlueDogRequirements::AbortLatchDeadline {
        source = "Retained baseline S-110; BlueDogRequirementBasis::basisAbortLatchDeadline records its provisional allocation. No accepted originating value-selection trade is recorded.";
        applicability = "S-110 retains its own normative conditions and mission applicability: current/shared; selected configuration and conditions govern.";
        valueJustification = "Open: justify the actual limit in S-110 AbortLatchDeadline; mission motivation alone does not select that value.";
        marginBasis = "Open: record measurement uncertainty, variability and margin for S-110; no extra numerical margin is allocated by this decision record.";
        evidenceNeeded = "BlueDogRequirementVerification::EmergencyControlVerification; accepted configuration-specific measurements and the value-selection argument remain required.";
        owner = "Project owner; supporting assessment responsibility follows the named verification case.";
        closureAction = "Before release of S-110: Use installed observations and achieved maneuvers in representative and adverse encounters or emergency-control faults; compare the selected latency with complete response and safety margins. Record the retained or revised value, alternatives, evidence references, assumptions and acceptance disposition.";
        accepted = false;
    }
    metadata decisionRecoveryTelemetryCadence : AllocationDecision about BlueDogRequirements::RecoveryTelemetryCadence {
        source = "Retained baseline S-111; BlueDogRequirementBasis::basisRecoveryTelemetryCadence records its provisional allocation. No accepted originating value-selection trade is recorded.";
        applicability = "S-111 retains its own normative conditions and mission applicability: current/shared; selected configuration and conditions govern.";
        valueJustification = "Open: justify the actual limit in S-111 RecoveryTelemetryCadence; mission motivation alone does not select that value.";
        marginBasis = "Open: record measurement uncertainty, variability and margin for S-111; no extra numerical margin is allocated by this decision record.";
        evidenceNeeded = "BlueDogRequirementVerification::EmergencyControlVerification; accepted configuration-specific measurements and the value-selection argument remain required.";
        owner = "Project owner; supporting assessment responsibility follows the named verification case.";
        closureAction = "Before release of S-111: Use installed observations and achieved maneuvers in representative and adverse encounters or emergency-control faults; compare the selected latency with complete response and safety margins. Record the retained or revised value, alternatives, evidence references, assumptions and acceptance disposition.";
        accepted = false;
    }
    metadata decisionMotorIsolationDeadline : AllocationDecision about BlueDogRequirements::MotorIsolationDeadline {
        source = "Retained baseline S-112; BlueDogRequirementBasis::basisMotorIsolationDeadline records its provisional allocation. No accepted originating value-selection trade is recorded.";
        applicability = "S-112 retains its own normative conditions and mission applicability: current/shared; selected configuration and conditions govern.";
        valueJustification = "Open: justify the actual limit in S-112 MotorIsolationDeadline; mission motivation alone does not select that value.";
        marginBasis = "Open: record measurement uncertainty, variability and margin for S-112; no extra numerical margin is allocated by this decision record.";
        evidenceNeeded = "BlueDogRequirementVerification::EmergencyControlVerification; accepted configuration-specific measurements and the value-selection argument remain required.";
        owner = "Project owner; supporting assessment responsibility follows the named verification case.";
        closureAction = "Before release of S-112: Use installed observations and achieved maneuvers in representative and adverse encounters or emergency-control faults; compare the selected latency with complete response and safety margins. Record the retained or revised value, alternatives, evidence references, assumptions and acceptance disposition.";
        accepted = false;
    }
    metadata decisionManualControlLossShutdown : AllocationDecision about BlueDogRequirements::ManualControlLossShutdown {
        source = "Retained baseline S-114; BlueDogRequirementBasis::basisManualControlLossShutdown records its provisional allocation. No accepted originating value-selection trade is recorded.";
        applicability = "S-114 retains its own normative conditions and mission applicability: current/shared; selected configuration and conditions govern.";
        valueJustification = "Open: justify the actual limit in S-114 ManualControlLossShutdown; mission motivation alone does not select that value.";
        marginBasis = "Open: record measurement uncertainty, variability and margin for S-114; no extra numerical margin is allocated by this decision record.";
        evidenceNeeded = "BlueDogRequirementVerification::EmergencyControlVerification; accepted configuration-specific measurements and the value-selection argument remain required.";
        owner = "Project owner; supporting assessment responsibility follows the named verification case.";
        closureAction = "Before release of S-114: Use installed observations and achieved maneuvers in representative and adverse encounters or emergency-control faults; compare the selected latency with complete response and safety margins. Record the retained or revised value, alternatives, evidence references, assumptions and acceptance disposition.";
        accepted = false;
    }
    metadata decisionSignalingModeDeadline : AllocationDecision about BlueDogRequirements::SignalingModeDeadline {
        source = "Retained baseline S-119; BlueDogRequirementBasis::basisSignalingModeDeadline records its provisional allocation. No accepted originating value-selection trade is recorded.";
        applicability = "S-119 retains its own normative conditions and mission applicability: current/shared; selected configuration and conditions govern.";
        valueJustification = "Open: justify the actual limit in S-119 SignalingModeDeadline; mission motivation alone does not select that value.";
        marginBasis = "Open: record measurement uncertainty, variability and margin for S-119; no extra numerical margin is allocated by this decision record.";
        evidenceNeeded = "BlueDogRequirementVerification::NavigationConspicuityVerification; accepted configuration-specific measurements and the value-selection argument remain required.";
        owner = "Project owner; supporting assessment responsibility follows the named verification case.";
        closureAction = "Before release of S-119: Use installed observations and achieved maneuvers in representative and adverse encounters or emergency-control faults; compare the selected latency with complete response and safety margins. Record the retained or revised value, alternatives, evidence references, assumptions and acceptance disposition.";
        accepted = false;
    }
    metadata decisionSignalingFaultRecording : AllocationDecision about BlueDogRequirements::SignalingFaultRecording {
        source = "Retained baseline S-120; BlueDogRequirementBasis::basisSignalingFaultRecording records its provisional allocation. No accepted originating value-selection trade is recorded.";
        applicability = "S-120 retains its own normative conditions and mission applicability: current/shared; selected configuration and conditions govern.";
        valueJustification = "Open: justify the actual limit in S-120 SignalingFaultRecording; mission motivation alone does not select that value.";
        marginBasis = "Open: record measurement uncertainty, variability and margin for S-120; no extra numerical margin is allocated by this decision record.";
        evidenceNeeded = "BlueDogRequirementVerification::NavigationConspicuityVerification; accepted configuration-specific measurements and the value-selection argument remain required.";
        owner = "Project owner; supporting assessment responsibility follows the named verification case.";
        closureAction = "Before release of S-120: Use installed observations and achieved maneuvers in representative and adverse encounters or emergency-control faults; compare the selected latency with complete response and safety margins. Record the retained or revised value, alternatives, evidence references, assumptions and acceptance disposition.";
        accepted = false;
    }
    metadata decisionSignalingFaultReporting : AllocationDecision about BlueDogRequirements::SignalingFaultReporting {
        source = "Retained baseline S-121; BlueDogRequirementBasis::basisSignalingFaultReporting records its provisional allocation. No accepted originating value-selection trade is recorded.";
        applicability = "S-121 retains its own normative conditions and mission applicability: current/shared; selected configuration and conditions govern.";
        valueJustification = "Open: justify the actual limit in S-121 SignalingFaultReporting; mission motivation alone does not select that value.";
        marginBasis = "Open: record measurement uncertainty, variability and margin for S-121; no extra numerical margin is allocated by this decision record.";
        evidenceNeeded = "BlueDogRequirementVerification::NavigationConspicuityVerification; accepted configuration-specific measurements and the value-selection argument remain required.";
        owner = "Project owner; supporting assessment responsibility follows the named verification case.";
        closureAction = "Before release of S-121: Use installed observations and achieved maneuvers in representative and adverse encounters or emergency-control faults; compare the selected latency with complete response and safety margins. Record the retained or revised value, alternatives, evidence references, assumptions and acceptance disposition.";
        accepted = false;
    }
    metadata decisionExpiredCommandRejection : AllocationDecision about BlueDogRequirements::ExpiredCommandRejection {
        source = "Retained baseline C-207; BlueDogRequirementBasis::basisExpiredCommandRejection records its provisional allocation. No accepted originating value-selection trade is recorded.";
        applicability = "C-207 retains its own normative conditions and mission applicability: current/shared; selected configuration and conditions govern.";
        valueJustification = "Open: justify the actual limit in C-207 ExpiredCommandRejection; mission motivation alone does not select that value.";
        marginBasis = "Open: record measurement uncertainty, variability and margin for C-207; no extra numerical margin is allocated by this decision record.";
        evidenceNeeded = "BlueDogRequirementVerification::CommandIntegrityVerification; accepted configuration-specific measurements and the value-selection argument remain required.";
        owner = "Project owner; supporting assessment responsibility follows the named verification case.";
        closureAction = "Before release of C-207: Measure end-to-end telemetry or command handling under delays, reconnects and invalid/replayed input; compare the selected timing with operator interpretation and persistent qualification behavior. Record the retained or revised value, alternatives, evidence references, assumptions and acceptance disposition.";
        accepted = false;
    }
    metadata decisionAcceptedCommandDeadline : AllocationDecision about BlueDogRequirements::AcceptedCommandDeadline {
        source = "Retained baseline C-208; BlueDogRequirementBasis::basisAcceptedCommandDeadline records its provisional allocation. No accepted originating value-selection trade is recorded.";
        applicability = "C-208 retains its own normative conditions and mission applicability: current/shared; selected configuration and conditions govern.";
        valueJustification = "Open: justify the actual limit in C-208 AcceptedCommandDeadline; mission motivation alone does not select that value.";
        marginBasis = "Open: record measurement uncertainty, variability and margin for C-208; no extra numerical margin is allocated by this decision record.";
        evidenceNeeded = "BlueDogRequirementVerification::CommandIntegrityVerification; accepted configuration-specific measurements and the value-selection argument remain required.";
        owner = "Project owner; supporting assessment responsibility follows the named verification case.";
        closureAction = "Before release of C-208: Measure end-to-end telemetry or command handling under delays, reconnects and invalid/replayed input; compare the selected timing with operator interpretation and persistent qualification behavior. Record the retained or revised value, alternatives, evidence references, assumptions and acceptance disposition.";
        accepted = false;
    }
    metadata decisionOnboardAcknowledgmentDeadline : AllocationDecision about BlueDogRequirements::OnboardAcknowledgmentDeadline {
        source = "Retained baseline C-209; BlueDogRequirementBasis::basisOnboardAcknowledgmentDeadline records its provisional allocation. No accepted originating value-selection trade is recorded.";
        applicability = "C-209 retains its own normative conditions and mission applicability: current/shared; selected configuration and conditions govern.";
        valueJustification = "Open: justify the actual limit in C-209 OnboardAcknowledgmentDeadline; mission motivation alone does not select that value.";
        marginBasis = "Open: record measurement uncertainty, variability and margin for C-209; no extra numerical margin is allocated by this decision record.";
        evidenceNeeded = "BlueDogRequirementVerification::CommandIntegrityVerification; accepted configuration-specific measurements and the value-selection argument remain required.";
        owner = "Project owner; supporting assessment responsibility follows the named verification case.";
        closureAction = "Before release of C-209: Measure end-to-end telemetry or command handling under delays, reconnects and invalid/replayed input; compare the selected timing with operator interpretation and persistent qualification behavior. Record the retained or revised value, alternatives, evidence references, assumptions and acceptance disposition.";
        accepted = false;
    }
    metadata decisionGorgeWind : AllocationDecision about BlueDogRequirements::GorgeWind {
        source = "Retained baseline N-011; BlueDogRequirementBasis::basisGorgeWind records its provisional allocation. No accepted originating value-selection trade is recorded.";
        applicability = "N-011 retains its own normative conditions and mission applicability: current/shared; selected configuration and conditions govern.";
        valueJustification = "Open: justify the actual limit in N-011 GorgeWind; mission motivation alone does not select that value.";
        marginBasis = "Open: record measurement uncertainty, variability and margin for N-011; no extra numerical margin is allocated by this decision record.";
        evidenceNeeded = "BlueDogRequirementVerification::GorgeWindVerification; accepted configuration-specific measurements and the value-selection argument remain required.";
        owner = "Project owner; supporting assessment responsibility follows the named verification case.";
        closureAction = "Before release of N-011: Establish representative site/casualty exposure and configuration-specific functional recovery; compare the selected boundary or response limit with measured failure margins and interacting exposures. Record the retained or revised value, alternatives, evidence references, assumptions and acceptance disposition.";
        accepted = false;
    }
    metadata decisionGorgeWaves : AllocationDecision about BlueDogRequirements::GorgeWaves {
        source = "Retained baseline N-012; BlueDogRequirementBasis::basisGorgeWaves records its provisional allocation. No accepted originating value-selection trade is recorded.";
        applicability = "N-012 retains its own normative conditions and mission applicability: current/shared; selected configuration and conditions govern.";
        valueJustification = "Open: justify the actual limit in N-012 GorgeWaves; mission motivation alone does not select that value.";
        marginBasis = "Open: record measurement uncertainty, variability and margin for N-012; no extra numerical margin is allocated by this decision record.";
        evidenceNeeded = "BlueDogRequirementVerification::GorgeWavesVerification; accepted configuration-specific measurements and the value-selection argument remain required.";
        owner = "Project owner; supporting assessment responsibility follows the named verification case.";
        closureAction = "Before release of N-012: Establish representative site/casualty exposure and configuration-specific functional recovery; compare the selected boundary or response limit with measured failure margins and interacting exposures. Record the retained or revised value, alternatives, evidence references, assumptions and acceptance disposition.";
        accepted = false;
    }
    metadata decisionGorgeCurrent : AllocationDecision about BlueDogRequirements::GorgeCurrent {
        source = "Retained baseline N-013; BlueDogRequirementBasis::basisGorgeCurrent records its provisional allocation. No accepted originating value-selection trade is recorded.";
        applicability = "N-013 retains its own normative conditions and mission applicability: current/shared; selected configuration and conditions govern.";
        valueJustification = "Open: justify the actual limit in N-013 GorgeCurrent; mission motivation alone does not select that value.";
        marginBasis = "Open: record measurement uncertainty, variability and margin for N-013; no extra numerical margin is allocated by this decision record.";
        evidenceNeeded = "BlueDogRequirementVerification::GorgeCurrentVerification; accepted configuration-specific measurements and the value-selection argument remain required.";
        owner = "Project owner; supporting assessment responsibility follows the named verification case.";
        closureAction = "Before release of N-013: Establish representative site/casualty exposure and configuration-specific functional recovery; compare the selected boundary or response limit with measured failure margins and interacting exposures. Record the retained or revised value, alternatives, evidence references, assumptions and acceptance disposition.";
        accepted = false;
    }
    metadata decisionGorgeSurvivalWind : AllocationDecision about BlueDogRequirements::GorgeSurvivalWind {
        source = "Retained baseline N-014; BlueDogRequirementBasis::basisGorgeSurvivalWind records its provisional allocation. No accepted originating value-selection trade is recorded.";
        applicability = "N-014 retains its own normative conditions and mission applicability: current/shared; selected configuration and conditions govern.";
        valueJustification = "Open: justify the actual limit in N-014 GorgeSurvivalWind; mission motivation alone does not select that value.";
        marginBasis = "Open: record measurement uncertainty, variability and margin for N-014; no extra numerical margin is allocated by this decision record.";
        evidenceNeeded = "BlueDogRequirementVerification::EnvironmentalEnvelopeVerification; accepted configuration-specific measurements and the value-selection argument remain required.";
        owner = "Project owner; supporting assessment responsibility follows the named verification case.";
        closureAction = "Before release of N-014: Establish representative site/casualty exposure and configuration-specific functional recovery; compare the selected boundary or response limit with measured failure margins and interacting exposures. Record the retained or revised value, alternatives, evidence references, assumptions and acceptance disposition.";
        accepted = false;
    }
    metadata decisionGorgeSurvivalWaves : AllocationDecision about BlueDogRequirements::GorgeSurvivalWaves {
        source = "Retained baseline N-015; BlueDogRequirementBasis::basisGorgeSurvivalWaves records its provisional allocation. No accepted originating value-selection trade is recorded.";
        applicability = "N-015 retains its own normative conditions and mission applicability: current/shared; selected configuration and conditions govern.";
        valueJustification = "Open: justify the actual limit in N-015 GorgeSurvivalWaves; mission motivation alone does not select that value.";
        marginBasis = "Open: record measurement uncertainty, variability and margin for N-015; no extra numerical margin is allocated by this decision record.";
        evidenceNeeded = "BlueDogRequirementVerification::GorgeSurvivalWavesVerification; accepted configuration-specific measurements and the value-selection argument remain required.";
        owner = "Project owner; supporting assessment responsibility follows the named verification case.";
        closureAction = "Before release of N-015: Establish representative site/casualty exposure and configuration-specific functional recovery; compare the selected boundary or response limit with measured failure margins and interacting exposures. Record the retained or revised value, alternatives, evidence references, assumptions and acceptance disposition.";
        accepted = false;
    }
    metadata decisionAirTemperature : AllocationDecision about BlueDogRequirements::AirTemperature {
        source = "Retained baseline N-030; BlueDogRequirementBasis::basisAirTemperature records its provisional allocation. No accepted originating value-selection trade is recorded.";
        applicability = "N-030 retains its own normative conditions and mission applicability: current/shared; selected configuration and conditions govern.";
        valueJustification = "Open: justify the actual limit in N-030 AirTemperature; mission motivation alone does not select that value.";
        marginBasis = "Open: record measurement uncertainty, variability and margin for N-030; no extra numerical margin is allocated by this decision record.";
        evidenceNeeded = "BlueDogRequirementVerification::AirTemperatureVerification; accepted configuration-specific measurements and the value-selection argument remain required.";
        owner = "Project owner; supporting assessment responsibility follows the named verification case.";
        closureAction = "Before release of N-030: Establish representative site/casualty exposure and configuration-specific functional recovery; compare the selected boundary or response limit with measured failure margins and interacting exposures. Record the retained or revised value, alternatives, evidence references, assumptions and acceptance disposition.";
        accepted = false;
    }
    metadata decisionWaterTemperature : AllocationDecision about BlueDogRequirements::WaterTemperature {
        source = "Retained baseline N-031; BlueDogRequirementBasis::basisWaterTemperature records its provisional allocation. No accepted originating value-selection trade is recorded.";
        applicability = "N-031 retains its own normative conditions and mission applicability: current/shared; selected configuration and conditions govern.";
        valueJustification = "Open: justify the actual limit in N-031 WaterTemperature; mission motivation alone does not select that value.";
        marginBasis = "Open: record measurement uncertainty, variability and margin for N-031; no extra numerical margin is allocated by this decision record.";
        evidenceNeeded = "BlueDogRequirementVerification::WaterTemperatureVerification; accepted configuration-specific measurements and the value-selection argument remain required.";
        owner = "Project owner; supporting assessment responsibility follows the named verification case.";
        closureAction = "Before release of N-031: Establish representative site/casualty exposure and configuration-specific functional recovery; compare the selected boundary or response limit with measured failure margins and interacting exposures. Record the retained or revised value, alternatives, evidence references, assumptions and acceptance disposition.";
        accepted = false;
    }
    metadata decisionHumidity : AllocationDecision about BlueDogRequirements::Humidity {
        source = "Retained baseline N-032; BlueDogRequirementBasis::basisHumidity records its provisional allocation. No accepted originating value-selection trade is recorded.";
        applicability = "N-032 retains its own normative conditions and mission applicability: current/shared; selected configuration and conditions govern.";
        valueJustification = "Open: justify the actual limit in N-032 Humidity; mission motivation alone does not select that value.";
        marginBasis = "Open: record measurement uncertainty, variability and margin for N-032; no extra numerical margin is allocated by this decision record.";
        evidenceNeeded = "BlueDogRequirementVerification::HumidityVerification; accepted configuration-specific measurements and the value-selection argument remain required.";
        owner = "Project owner; supporting assessment responsibility follows the named verification case.";
        closureAction = "Before release of N-032: Establish representative site/casualty exposure and configuration-specific functional recovery; compare the selected boundary or response limit with measured failure margins and interacting exposures. Record the retained or revised value, alternatives, evidence references, assumptions and acceptance disposition.";
        accepted = false;
    }
    metadata decisionVisibility : AllocationDecision about BlueDogRequirements::Visibility {
        source = "Retained baseline N-033; BlueDogRequirementBasis::basisVisibility records its provisional allocation. No accepted originating value-selection trade is recorded.";
        applicability = "N-033 retains its own normative conditions and mission applicability: current/shared; selected configuration and conditions govern.";
        valueJustification = "Open: justify the actual limit in N-033 Visibility; mission motivation alone does not select that value.";
        marginBasis = "Open: record measurement uncertainty, variability and margin for N-033; no extra numerical margin is allocated by this decision record.";
        evidenceNeeded = "BlueDogRequirementVerification::VisibilityVerification; accepted configuration-specific measurements and the value-selection argument remain required.";
        owner = "Project owner; supporting assessment responsibility follows the named verification case.";
        closureAction = "Before release of N-033: Establish representative site/casualty exposure and configuration-specific functional recovery; compare the selected boundary or response limit with measured failure margins and interacting exposures. Record the retained or revised value, alternatives, evidence references, assumptions and acceptance disposition.";
        accepted = false;
    }
    metadata decisionCalmOperation : AllocationDecision about BlueDogRequirements::CalmOperation {
        source = "Retained baseline N-034; BlueDogRequirementBasis::basisCalmOperation records its provisional allocation. No accepted originating value-selection trade is recorded.";
        applicability = "N-034 retains its own normative conditions and mission applicability: current/shared; selected configuration and conditions govern.";
        valueJustification = "Open: justify the actual limit in N-034 CalmOperation; mission motivation alone does not select that value.";
        marginBasis = "Open: record measurement uncertainty, variability and margin for N-034; no extra numerical margin is allocated by this decision record.";
        evidenceNeeded = "BlueDogRequirementVerification::CalmOperationVerification; accepted configuration-specific measurements and the value-selection argument remain required.";
        owner = "Project owner; supporting assessment responsibility follows the named verification case.";
        closureAction = "Before release of N-034: Establish representative site/casualty exposure and configuration-specific functional recovery; compare the selected boundary or response limit with measured failure margins and interacting exposures. Record the retained or revised value, alternatives, evidence references, assumptions and acceptance disposition.";
        accepted = false;
    }
    metadata decisionEnvelopeTransition : AllocationDecision about BlueDogRequirements::EnvelopeTransition {
        source = "Retained baseline N-035; BlueDogRequirementBasis::basisEnvelopeTransition records its provisional allocation. No accepted originating value-selection trade is recorded.";
        applicability = "N-035 retains its own normative conditions and mission applicability: current/shared; selected configuration and conditions govern.";
        valueJustification = "Open: justify the actual limit in N-035 EnvelopeTransition; mission motivation alone does not select that value.";
        marginBasis = "Open: record measurement uncertainty, variability and margin for N-035; no extra numerical margin is allocated by this decision record.";
        evidenceNeeded = "BlueDogRequirementVerification::EnvelopeTransitionVerification; accepted configuration-specific measurements and the value-selection argument remain required.";
        owner = "Project owner; supporting assessment responsibility follows the named verification case.";
        closureAction = "Before release of N-035: Establish representative site/casualty exposure and configuration-specific functional recovery; compare the selected boundary or response limit with measured failure margins and interacting exposures. Record the retained or revised value, alternatives, evidence references, assumptions and acceptance disposition.";
        accepted = false;
    }
    metadata decisionEnclosureSealing : AllocationDecision about BlueDogRequirements::EnclosureSealing {
        source = "Retained baseline N-043; BlueDogRequirementBasis::basisEnclosureSealing records its provisional allocation. No accepted originating value-selection trade is recorded.";
        applicability = "N-043 retains its own normative conditions and mission applicability: current/shared; selected configuration and conditions govern.";
        valueJustification = "Open: justify the actual limit in N-043 EnclosureSealing; mission motivation alone does not select that value.";
        marginBasis = "Open: record measurement uncertainty, variability and margin for N-043; no extra numerical margin is allocated by this decision record.";
        evidenceNeeded = "BlueDogRequirementVerification::EnvironmentalEnvelopeVerification; accepted configuration-specific measurements and the value-selection argument remain required.";
        owner = "Project owner; supporting assessment responsibility follows the named verification case.";
        closureAction = "Before release of N-043: Establish representative site/casualty exposure and configuration-specific functional recovery; compare the selected boundary or response limit with measured failure margins and interacting exposures. Record the retained or revised value, alternatives, evidence references, assumptions and acceptance disposition.";
        accepted = false;
    }
    metadata decisionSolarHeating : AllocationDecision about BlueDogRequirements::SolarHeating {
        source = "Retained baseline N-046; BlueDogRequirementBasis::basisSolarHeating records its provisional allocation. No accepted originating value-selection trade is recorded.";
        applicability = "N-046 retains its own normative conditions and mission applicability: current/shared; selected configuration and conditions govern.";
        valueJustification = "Open: justify the actual limit in N-046 SolarHeating; mission motivation alone does not select that value.";
        marginBasis = "Open: record measurement uncertainty, variability and margin for N-046; no extra numerical margin is allocated by this decision record.";
        evidenceNeeded = "BlueDogRequirementVerification::SolarHeatingVerification; accepted configuration-specific measurements and the value-selection argument remain required.";
        owner = "Project owner; supporting assessment responsibility follows the named verification case.";
        closureAction = "Before release of N-046: Establish representative site/casualty exposure and configuration-specific functional recovery; compare the selected boundary or response limit with measured failure margins and interacting exposures. Record the retained or revised value, alternatives, evidence references, assumptions and acceptance disposition.";
        accepted = false;
    }
    metadata decisionSubmergedWeedPassage : AllocationDecision about BlueDogRequirements::SubmergedWeedPassage {
        source = "Retained baseline N-053; BlueDogRequirementBasis::basisSubmergedWeedPassage records its provisional allocation. No accepted originating value-selection trade is recorded.";
        applicability = "N-053 retains its own normative conditions and mission applicability: current/shared; selected configuration and conditions govern.";
        valueJustification = "Open: justify the actual limit in N-053 SubmergedWeedPassage; mission motivation alone does not select that value.";
        marginBasis = "Open: record measurement uncertainty, variability and margin for N-053; no extra numerical margin is allocated by this decision record.";
        evidenceNeeded = "BlueDogRequirementVerification::SubmergedWeedPassageVerification; accepted configuration-specific measurements and the value-selection argument remain required.";
        owner = "Project owner; supporting assessment responsibility follows the named verification case.";
        closureAction = "Before release of N-053: Establish representative site/casualty exposure and configuration-specific functional recovery; compare the selected boundary or response limit with measured failure margins and interacting exposures. Record the retained or revised value, alternatives, evidence references, assumptions and acceptance disposition.";
        accepted = false;
    }
    metadata decisionWeedSnagShedding : AllocationDecision about BlueDogRequirements::WeedSnagShedding {
        source = "Retained baseline N-054; BlueDogRequirementBasis::basisWeedSnagShedding records its provisional allocation. No accepted originating value-selection trade is recorded.";
        applicability = "N-054 retains its own normative conditions and mission applicability: current/shared; selected configuration and conditions govern.";
        valueJustification = "Open: justify the actual limit in N-054 WeedSnagShedding; mission motivation alone does not select that value.";
        marginBasis = "Open: record measurement uncertainty, variability and margin for N-054; no extra numerical margin is allocated by this decision record.";
        evidenceNeeded = "BlueDogRequirementVerification::WeedSnagSheddingVerification; accepted configuration-specific measurements and the value-selection argument remain required.";
        owner = "Project owner; supporting assessment responsibility follows the named verification case.";
        closureAction = "Before release of N-054: Establish representative site/casualty exposure and configuration-specific functional recovery; compare the selected boundary or response limit with measured failure margins and interacting exposures. Record the retained or revised value, alternatives, evidence references, assumptions and acceptance disposition.";
        accepted = false;
    }
    metadata decisionWeedBlockageResponse : AllocationDecision about BlueDogRequirements::WeedBlockageResponse {
        source = "Retained baseline N-055; BlueDogRequirementBasis::basisWeedBlockageResponse records its provisional allocation. No accepted originating value-selection trade is recorded.";
        applicability = "N-055 retains its own normative conditions and mission applicability: current/shared; selected configuration and conditions govern.";
        valueJustification = "Open: justify the actual limit in N-055 WeedBlockageResponse; mission motivation alone does not select that value.";
        marginBasis = "Open: record measurement uncertainty, variability and margin for N-055; no extra numerical margin is allocated by this decision record.";
        evidenceNeeded = "BlueDogRequirementVerification::WeedBlockageResponseVerification; accepted configuration-specific measurements and the value-selection argument remain required.";
        owner = "Project owner; supporting assessment responsibility follows the named verification case.";
        closureAction = "Before release of N-055: Establish representative site/casualty exposure and configuration-specific functional recovery; compare the selected boundary or response limit with measured failure margins and interacting exposures. Record the retained or revised value, alternatives, evidence references, assumptions and acceptance disposition.";
        accepted = false;
    }
    metadata decisionRecoveryPropulsorWeeds : AllocationDecision about BlueDogRequirements::RecoveryPropulsorWeeds {
        source = "Retained baseline N-056; BlueDogRequirementBasis::basisRecoveryPropulsorWeeds records its provisional allocation. No accepted originating value-selection trade is recorded.";
        applicability = "N-056 retains its own normative conditions and mission applicability: current/shared; selected configuration and conditions govern.";
        valueJustification = "Open: justify the actual limit in N-056 RecoveryPropulsorWeeds; mission motivation alone does not select that value.";
        marginBasis = "Open: record measurement uncertainty, variability and margin for N-056; no extra numerical margin is allocated by this decision record.";
        evidenceNeeded = "BlueDogRequirementVerification::RecoveryPropulsorWeedsVerification; accepted configuration-specific measurements and the value-selection argument remain required.";
        owner = "Project owner; supporting assessment responsibility follows the named verification case.";
        closureAction = "Before release of N-056: Establish representative site/casualty exposure and configuration-specific functional recovery; compare the selected boundary or response limit with measured failure margins and interacting exposures. Record the retained or revised value, alternatives, evidence references, assumptions and acceptance disposition.";
        accepted = false;
    }
    metadata decisionRestrictedVisibilityEntry : AllocationDecision about BlueDogRequirements::RestrictedVisibilityEntry {
        source = "Retained baseline N-103; BlueDogRequirementBasis::basisRestrictedVisibilityEntry records its provisional allocation. No accepted originating value-selection trade is recorded.";
        applicability = "N-103 retains its own normative conditions and mission applicability: current/shared; selected configuration and conditions govern.";
        valueJustification = "Open: justify the actual limit in N-103 RestrictedVisibilityEntry; mission motivation alone does not select that value.";
        marginBasis = "Open: record measurement uncertainty, variability and margin for N-103; no extra numerical margin is allocated by this decision record.";
        evidenceNeeded = "BlueDogRequirementVerification::VisibilityVerification; accepted configuration-specific measurements and the value-selection argument remain required.";
        owner = "Project owner; supporting assessment responsibility follows the named verification case.";
        closureAction = "Before release of N-103: Establish representative site/casualty exposure and configuration-specific functional recovery; compare the selected boundary or response limit with measured failure margins and interacting exposures. Record the retained or revised value, alternatives, evidence references, assumptions and acceptance disposition.";
        accepted = false;
    }
    metadata decisionSurvivalEntryDeadline : AllocationDecision about BlueDogRequirements::SurvivalEntryDeadline {
        source = "Retained baseline N-106; BlueDogRequirementBasis::basisSurvivalEntryDeadline records its provisional allocation. No accepted originating value-selection trade is recorded.";
        applicability = "N-106 retains its own normative conditions and mission applicability: current/shared; selected configuration and conditions govern.";
        valueJustification = "Open: justify the actual limit in N-106 SurvivalEntryDeadline; mission motivation alone does not select that value.";
        marginBasis = "Open: record measurement uncertainty, variability and margin for N-106; no extra numerical margin is allocated by this decision record.";
        evidenceNeeded = "BlueDogRequirementVerification::EnvelopeTransitionVerification; accepted configuration-specific measurements and the value-selection argument remain required.";
        owner = "Project owner; supporting assessment responsibility follows the named verification case.";
        closureAction = "Before release of N-106: Establish representative site/casualty exposure and configuration-specific functional recovery; compare the selected boundary or response limit with measured failure margins and interacting exposures. Record the retained or revised value, alternatives, evidence references, assumptions and acceptance disposition.";
        accepted = false;
    }
    metadata decisionSailingResumptionDeadline : AllocationDecision about BlueDogRequirements::SailingResumptionDeadline {
        source = "Retained baseline N-108; BlueDogRequirementBasis::basisSailingResumptionDeadline records its provisional allocation. No accepted originating value-selection trade is recorded.";
        applicability = "N-108 retains its own normative conditions and mission applicability: current/shared; selected configuration and conditions govern.";
        valueJustification = "Open: justify the actual limit in N-108 SailingResumptionDeadline; mission motivation alone does not select that value.";
        marginBasis = "Open: record measurement uncertainty, variability and margin for N-108; no extra numerical margin is allocated by this decision record.";
        evidenceNeeded = "BlueDogRequirementVerification::EnvelopeTransitionVerification; accepted configuration-specific measurements and the value-selection argument remain required.";
        owner = "Project owner; supporting assessment responsibility follows the named verification case.";
        closureAction = "Before release of N-108: Establish representative site/casualty exposure and configuration-specific functional recovery; compare the selected boundary or response limit with measured failure margins and interacting exposures. Record the retained or revised value, alternatives, evidence references, assumptions and acceptance disposition.";
        accepted = false;
    }
    metadata decisionWetConductorResistance : AllocationDecision about BlueDogRequirements::WetConductorResistance {
        source = "Retained baseline N-113; BlueDogRequirementBasis::basisWetConductorResistance records its provisional allocation. No accepted originating value-selection trade is recorded.";
        applicability = "N-113 retains its own normative conditions and mission applicability: current/shared; selected configuration and conditions govern.";
        valueJustification = "Open: justify the actual limit in N-113 WetConductorResistance; mission motivation alone does not select that value.";
        marginBasis = "Open: record measurement uncertainty, variability and margin for N-113; no extra numerical margin is allocated by this decision record.";
        evidenceNeeded = "BlueDogRequirementVerification::WetElectricalIntegrityVerification; accepted configuration-specific measurements and the value-selection argument remain required.";
        owner = "Project owner; supporting assessment responsibility follows the named verification case.";
        closureAction = "Before release of N-113: Establish representative site/casualty exposure and configuration-specific functional recovery; compare the selected boundary or response limit with measured failure margins and interacting exposures. Record the retained or revised value, alternatives, evidence references, assumptions and acceptance disposition.";
        accepted = false;
    }
    metadata decisionWetInsulationResistance : AllocationDecision about BlueDogRequirements::WetInsulationResistance {
        source = "Retained baseline N-114; BlueDogRequirementBasis::basisWetInsulationResistance records its provisional allocation. No accepted originating value-selection trade is recorded.";
        applicability = "N-114 retains its own normative conditions and mission applicability: current/shared; selected configuration and conditions govern.";
        valueJustification = "Open: justify the actual limit in N-114 WetInsulationResistance; mission motivation alone does not select that value.";
        marginBasis = "Open: record measurement uncertainty, variability and margin for N-114; no extra numerical margin is allocated by this decision record.";
        evidenceNeeded = "BlueDogRequirementVerification::WetElectricalIntegrityVerification; accepted configuration-specific measurements and the value-selection argument remain required.";
        owner = "Project owner; supporting assessment responsibility follows the named verification case.";
        closureAction = "Before release of N-114: Establish representative site/casualty exposure and configuration-specific functional recovery; compare the selected boundary or response limit with measured failure margins and interacting exposures. Record the retained or revised value, alternatives, evidence references, assumptions and acceptance disposition.";
        accepted = false;
    }
    metadata decisionWeedPassageSpeed : AllocationDecision about BlueDogRequirements::WeedPassageSpeed {
        source = "Retained baseline N-126; BlueDogRequirementBasis::basisWeedPassageSpeed records its provisional allocation. No accepted originating value-selection trade is recorded.";
        applicability = "N-126 retains its own normative conditions and mission applicability: current/shared; selected configuration and conditions govern.";
        valueJustification = "Open: justify the actual limit in N-126 WeedPassageSpeed; mission motivation alone does not select that value.";
        marginBasis = "Open: record measurement uncertainty, variability and margin for N-126; no extra numerical margin is allocated by this decision record.";
        evidenceNeeded = "BlueDogRequirementVerification::SubmergedWeedPassageVerification; accepted configuration-specific measurements and the value-selection argument remain required.";
        owner = "Project owner; supporting assessment responsibility follows the named verification case.";
        closureAction = "Before release of N-126: Establish representative site/casualty exposure and configuration-specific functional recovery; compare the selected boundary or response limit with measured failure margins and interacting exposures. Record the retained or revised value, alternatives, evidence references, assumptions and acceptance disposition.";
        accepted = false;
    }
    metadata decisionWeedPassageSteering : AllocationDecision about BlueDogRequirements::WeedPassageSteering {
        source = "Retained baseline N-127; BlueDogRequirementBasis::basisWeedPassageSteering records its provisional allocation. No accepted originating value-selection trade is recorded.";
        applicability = "N-127 retains its own normative conditions and mission applicability: current/shared; selected configuration and conditions govern.";
        valueJustification = "Open: justify the actual limit in N-127 WeedPassageSteering; mission motivation alone does not select that value.";
        marginBasis = "Open: record measurement uncertainty, variability and margin for N-127; no extra numerical margin is allocated by this decision record.";
        evidenceNeeded = "BlueDogRequirementVerification::SubmergedWeedPassageVerification; accepted configuration-specific measurements and the value-selection argument remain required.";
        owner = "Project owner; supporting assessment responsibility follows the named verification case.";
        closureAction = "Before release of N-127: Establish representative site/casualty exposure and configuration-specific functional recovery; compare the selected boundary or response limit with measured failure margins and interacting exposures. Record the retained or revised value, alternatives, evidence references, assumptions and acceptance disposition.";
        accepted = false;
    }
    metadata decisionWeedSnagSpeedRecovery : AllocationDecision about BlueDogRequirements::WeedSnagSpeedRecovery {
        source = "Retained baseline N-128; BlueDogRequirementBasis::basisWeedSnagSpeedRecovery records its provisional allocation. No accepted originating value-selection trade is recorded.";
        applicability = "N-128 retains its own normative conditions and mission applicability: current/shared; selected configuration and conditions govern.";
        valueJustification = "Open: justify the actual limit in N-128 WeedSnagSpeedRecovery; mission motivation alone does not select that value.";
        marginBasis = "Open: record measurement uncertainty, variability and margin for N-128; no extra numerical margin is allocated by this decision record.";
        evidenceNeeded = "BlueDogRequirementVerification::WeedSnagSheddingVerification; accepted configuration-specific measurements and the value-selection argument remain required.";
        owner = "Project owner; supporting assessment responsibility follows the named verification case.";
        closureAction = "Before release of N-128: Establish representative site/casualty exposure and configuration-specific functional recovery; compare the selected boundary or response limit with measured failure margins and interacting exposures. Record the retained or revised value, alternatives, evidence references, assumptions and acceptance disposition.";
        accepted = false;
    }
    metadata decisionWeedSnagSteeringRecovery : AllocationDecision about BlueDogRequirements::WeedSnagSteeringRecovery {
        source = "Retained baseline N-129; BlueDogRequirementBasis::basisWeedSnagSteeringRecovery records its provisional allocation. No accepted originating value-selection trade is recorded.";
        applicability = "N-129 retains its own normative conditions and mission applicability: current/shared; selected configuration and conditions govern.";
        valueJustification = "Open: justify the actual limit in N-129 WeedSnagSteeringRecovery; mission motivation alone does not select that value.";
        marginBasis = "Open: record measurement uncertainty, variability and margin for N-129; no extra numerical margin is allocated by this decision record.";
        evidenceNeeded = "BlueDogRequirementVerification::WeedSnagSheddingVerification; accepted configuration-specific measurements and the value-selection argument remain required.";
        owner = "Project owner; supporting assessment responsibility follows the named verification case.";
        closureAction = "Before release of N-129: Establish representative site/casualty exposure and configuration-specific functional recovery; compare the selected boundary or response limit with measured failure margins and interacting exposures. Record the retained or revised value, alternatives, evidence references, assumptions and acceptance disposition.";
        accepted = false;
    }
    metadata decisionWeedBlockageFault : AllocationDecision about BlueDogRequirements::WeedBlockageFault {
        source = "Retained baseline N-130; BlueDogRequirementBasis::basisWeedBlockageFault records its provisional allocation. No accepted originating value-selection trade is recorded.";
        applicability = "N-130 retains its own normative conditions and mission applicability: current/shared; selected configuration and conditions govern.";
        valueJustification = "Open: justify the actual limit in N-130 WeedBlockageFault; mission motivation alone does not select that value.";
        marginBasis = "Open: record measurement uncertainty, variability and margin for N-130; no extra numerical margin is allocated by this decision record.";
        evidenceNeeded = "BlueDogRequirementVerification::WeedBlockageResponseVerification; accepted configuration-specific measurements and the value-selection argument remain required.";
        owner = "Project owner; supporting assessment responsibility follows the named verification case.";
        closureAction = "Before release of N-130: Establish representative site/casualty exposure and configuration-specific functional recovery; compare the selected boundary or response limit with measured failure margins and interacting exposures. Record the retained or revised value, alternatives, evidence references, assumptions and acceptance disposition.";
        accepted = false;
    }
    metadata decisionWeedBlockageContingency : AllocationDecision about BlueDogRequirements::WeedBlockageContingency {
        source = "Retained baseline N-131; BlueDogRequirementBasis::basisWeedBlockageContingency records its provisional allocation. No accepted originating value-selection trade is recorded.";
        applicability = "N-131 retains its own normative conditions and mission applicability: current/shared; selected configuration and conditions govern.";
        valueJustification = "Open: justify the actual limit in N-131 WeedBlockageContingency; mission motivation alone does not select that value.";
        marginBasis = "Open: record measurement uncertainty, variability and margin for N-131; no extra numerical margin is allocated by this decision record.";
        evidenceNeeded = "BlueDogRequirementVerification::WeedBlockageResponseVerification; accepted configuration-specific measurements and the value-selection argument remain required.";
        owner = "Project owner; supporting assessment responsibility follows the named verification case.";
        closureAction = "Before release of N-131: Establish representative site/casualty exposure and configuration-specific functional recovery; compare the selected boundary or response limit with measured failure margins and interacting exposures. Record the retained or revised value, alternatives, evidence references, assumptions and acceptance disposition.";
        accepted = false;
    }
    metadata decisionPoweredWeedSpeed : AllocationDecision about BlueDogRequirements::PoweredWeedSpeed {
        source = "Retained baseline N-133; BlueDogRequirementBasis::basisPoweredWeedSpeed records its provisional allocation. No accepted originating value-selection trade is recorded.";
        applicability = "N-133 retains its own normative conditions and mission applicability: current/shared; selected configuration and conditions govern.";
        valueJustification = "Open: justify the actual limit in N-133 PoweredWeedSpeed; mission motivation alone does not select that value.";
        marginBasis = "Open: record measurement uncertainty, variability and margin for N-133; no extra numerical margin is allocated by this decision record.";
        evidenceNeeded = "BlueDogRequirementVerification::RecoveryPropulsorWeedsVerification; accepted configuration-specific measurements and the value-selection argument remain required.";
        owner = "Project owner; supporting assessment responsibility follows the named verification case.";
        closureAction = "Before release of N-133: Establish representative site/casualty exposure and configuration-specific functional recovery; compare the selected boundary or response limit with measured failure margins and interacting exposures. Record the retained or revised value, alternatives, evidence references, assumptions and acceptance disposition.";
        accepted = false;
    }
    metadata decisionLockedPropulsorShutdown : AllocationDecision about BlueDogRequirements::LockedPropulsorShutdown {
        source = "Retained baseline N-136; BlueDogRequirementBasis::basisLockedPropulsorShutdown records its provisional allocation. No accepted originating value-selection trade is recorded.";
        applicability = "N-136 retains its own normative conditions and mission applicability: current/shared; selected configuration and conditions govern.";
        valueJustification = "Open: justify the actual limit in N-136 LockedPropulsorShutdown; mission motivation alone does not select that value.";
        marginBasis = "Open: record measurement uncertainty, variability and margin for N-136; no extra numerical margin is allocated by this decision record.";
        evidenceNeeded = "BlueDogRequirementVerification::RecoveryPropulsorWeedsVerification; accepted configuration-specific measurements and the value-selection argument remain required.";
        owner = "Project owner; supporting assessment responsibility follows the named verification case.";
        closureAction = "Before release of N-136: Establish representative site/casualty exposure and configuration-specific functional recovery; compare the selected boundary or response limit with measured failure margins and interacting exposures. Record the retained or revised value, alternatives, evidence references, assumptions and acceptance disposition.";
        accepted = false;
    }
    metadata decisionWindStaleInvalidation : AllocationDecision about BlueDogRequirements::WindStaleInvalidation {
        source = "Retained baseline E-149; BlueDogRequirementBasis::basisWindStaleInvalidation records its provisional allocation. No accepted originating value-selection trade is recorded.";
        applicability = "E-149 retains its own normative conditions and mission applicability: current/shared; selected configuration and conditions govern.";
        valueJustification = "Open: justify the actual limit in E-149 WindStaleInvalidation; mission motivation alone does not select that value.";
        marginBasis = "Open: record measurement uncertainty, variability and margin for E-149; no extra numerical margin is allocated by this decision record.";
        evidenceNeeded = "BlueDogRequirementVerification::WindObservationVerification; accepted configuration-specific measurements and the value-selection argument remain required.";
        owner = "Project owner; supporting assessment responsibility follows the named verification case.";
        closureAction = "Before release of E-149: Correlate the installed wind observation with a traceable reference across the declared flow/heel/trim matrix; reconcile local apparent-wind errors and the 10 m true-wind admission estimate before accepting the limit. Record the retained or revised value, alternatives, evidence references, assumptions and acceptance disposition.";
        accepted = false;
    }
    metadata decisionWindLossResponse : AllocationDecision about BlueDogRequirements::WindLossResponse {
        source = "Retained baseline E-151; BlueDogRequirementBasis::basisWindLossResponse records its provisional allocation. No accepted originating value-selection trade is recorded.";
        applicability = "E-151 retains its own normative conditions and mission applicability: current/shared; selected configuration and conditions govern.";
        valueJustification = "Open: justify the actual limit in E-151 WindLossResponse; mission motivation alone does not select that value.";
        marginBasis = "Open: record measurement uncertainty, variability and margin for E-151; no extra numerical margin is allocated by this decision record.";
        evidenceNeeded = "BlueDogRequirementVerification::WindObservationVerification; accepted configuration-specific measurements and the value-selection argument remain required.";
        owner = "Project owner; supporting assessment responsibility follows the named verification case.";
        closureAction = "Before release of E-151: Correlate the installed wind observation with a traceable reference across the declared flow/heel/trim matrix; reconcile local apparent-wind errors and the 10 m true-wind admission estimate before accepting the limit. Record the retained or revised value, alternatives, evidence references, assumptions and acceptance disposition.";
        accepted = false;
    }
    metadata procedureAirTemperatureVerification : AllocationDecision about BlueDogRequirementVerification::AirTemperatureVerification {
        source = "Planned procedure uses two hours at each stabilized air-temperature endpoint; this is a test-design choice, not another product requirement.";
        applicability = "Installed configuration and the associated environmental qualification conditions.";
        valueJustification = "Open: justify exposure duration and cycle count using thermal time constants, moisture transport, failure mechanisms and course/campaign representativeness.";
        marginBasis = "Open: record instrumentation uncertainty and duration/coverage margin.";
        evidenceNeeded = "Correlated temperature/moisture histories, stabilization evidence and review of cumulative and combined exposures.";
        owner = "Project owner, environmental assessment";
        closureAction = "Before accepting this procedure, establish representative exposure and coverage or revise the procedure; retain the associated product limits and inconclusive verdict until evidence is accepted.";
        accepted = false;
    }
    metadata procedureWaterTemperatureVerification : AllocationDecision about BlueDogRequirementVerification::WaterTemperatureVerification {
        source = "Planned procedure uses two hours at each stabilized water-temperature endpoint; this is a test-design choice, not another product requirement.";
        applicability = "Installed configuration and the associated environmental qualification conditions.";
        valueJustification = "Open: justify exposure duration and cycle count using thermal time constants, moisture transport, failure mechanisms and course/campaign representativeness.";
        marginBasis = "Open: record instrumentation uncertainty and duration/coverage margin.";
        evidenceNeeded = "Correlated temperature/moisture histories, stabilization evidence and review of cumulative and combined exposures.";
        owner = "Project owner, environmental assessment";
        closureAction = "Before accepting this procedure, establish representative exposure and coverage or revise the procedure; retain the associated product limits and inconclusive verdict until evidence is accepted.";
        accepted = false;
    }
    metadata procedureHumidityVerification : AllocationDecision about BlueDogRequirementVerification::HumidityVerification {
        source = "Planned procedure uses three powered 24-hour condensation cycles; this is a test-design choice, not another product requirement.";
        applicability = "Installed configuration and the associated environmental qualification conditions.";
        valueJustification = "Open: justify exposure duration and cycle count using thermal time constants, moisture transport, failure mechanisms and course/campaign representativeness.";
        marginBasis = "Open: record instrumentation uncertainty and duration/coverage margin.";
        evidenceNeeded = "Correlated temperature/moisture histories, stabilization evidence and review of cumulative and combined exposures.";
        owner = "Project owner, environmental assessment";
        closureAction = "Before accepting this procedure, establish representative exposure and coverage or revise the procedure; retain the associated product limits and inconclusive verdict until evidence is accepted.";
        accepted = false;
    }

}

package BlueDogRequirementDecisions {
    private import ScalarValues::*;
    part def OpenDecision {
        attribute question : String;
        attribute evidenceNeeded : String;
        attribute owner : String = "Project owner";
        attribute accepted : Boolean = false;
    }
    part <'U01'> trafficAcceptance : OpenDecision {
        attribute :>> question = "Accept class-specific observation, response, clearance and reliability/confidence criteria and the deployment applicability matrix.";
        attribute :>> evidenceNeeded = "Installed class-specific observations and achieved responses; configuration-specific rule review and recorded authority.";
    }
    dependency trafficAcceptanceBasis1 from trafficAcceptance to BlueDogRequirements::trafficSafety;
    dependency trafficAcceptanceBasis2 from trafficAcceptance to BlueDogRequirements::regulatoryClassification;
    dependency trafficAcceptanceBasis3 from trafficAcceptance to GorgeChallenge::navigationRuleApplicability;
    part <'U02'> recoveryAcceptance : OpenDecision {
        attribute :>> question = "Establish independent course-wide recovery and physical retrieval.";
        attribute :>> evidenceNeeded = "Surveyed accessible shores, final capture/retention, casualty propulsion, onboard observations/control and protected power under no-contact faults.";
    }
    dependency recoveryAcceptanceBasis1 from recoveryAcceptance to BlueDogRequirements::recoveryPropulsion;
    dependency recoveryAcceptanceBasis2 from recoveryAcceptance to BlueDogRequirements::recoveryEnergy;
    dependency recoveryAcceptanceBasis3 from recoveryAcceptance to GorgeChallenge::capsizeRecovery;
    part <'U03'> structuralQualification : OpenDecision {
        attribute :>> question = "Accept actual structural loads and installed functional limits.";
        attribute :>> evidenceNeeded = "Wet and aged production materials/joints, impact/fatigue/buckling and combined environmental load evidence.";
    }
    dependency structuralQualificationBasis1 from structuralQualification to BlueDogStructure::structuralIntegrity;
    part <'U04'> installedControlEvidence : OpenDecision {
        attribute :>> question = "Connect supplied observations and commands to installed sensing and achieved motion.";
        attribute :>> evidenceNeeded = "Correlated apparent and 10 m true wind, navigation/traffic observations, maneuver response and interacting faults.";
    }
    dependency installedControlEvidenceBasis1 from installedControlEvidence to BlueDogRequirements::windObservation;
    dependency installedControlEvidenceBasis2 from installedControlEvidence to BlueDogRequirements::navigationAndControl;
    part <'U05'> integrationCoverage : OpenDecision {
        attribute :>> question = "Establish an integrated acceptance argument beyond sampled predicates and supplied Booleans.";
        attribute :>> evidenceNeeded = "Compatible configuration-specific whole-route, safety, energy, structural and casualty evidence with justified coverage and exclusions.";
    }
    dependency integrationCoverageBasis1 from integrationCoverage to BlueDogRequirements::missionReliability;
    dependency integrationCoverageBasis2 from integrationCoverage to BlueDogRequirements::cruisePerformance;
    part <'U06'> futureMissionAcceptance : OpenDecision {
        attribute :>> question = "Select independently scoped future voyage targets and acceptance.";
        attribute :>> evidenceNeeded = "Hawaii route, weather, ocean exposure, sustained energy, communications, maintenance and recovery decisions.";
    }
    dependency futureMissionAcceptanceBasis1 from futureMissionAcceptance to BlueDogMissionScope::future;
}

package BlueDogRequirements {
    private import RequirementDerivation::*;
    private import ModelingMetadata::refinement;
    private import ScalarValues::*;
    private import ISQ::*;
    private import SI::*;
    private import GorgeChallenge::*;
    private import BlueDog::Goals::*;
    requirement def <'M-001'> RoundTrip {
        metadata workStatus : ModelingMetadata::StatusInfo { status = ModelingMetadata::StatusKind::open; }
        doc /* The vessel shall cross the configured Bingen departure, buoy 16 rounding checkpoints and Bingen return gates in order during one qualifying attempt. */
        comment conditions /* C-000 defines the governing finite challenge obligations. Course review, unassisted sail-only operation, safety capability, recovery reserve and the persistent attempt state apply throughout. Safe unassisted righting may preserve qualification; motor propulsion, external intervention or required safety-capability loss ends it. */
    }
    requirement def <'M-002'> MultiDayEndurance {
        metadata workStatus : ModelingMetadata::StatusInfo { status = ModelingMetadata::StatusKind::open; }
        doc /* The vessel shall complete the qualifying round trip without servicing or external charging. */
        comment conditions /* N-010 operational functions and applicable N-001 shared conditions apply. The mission history includes sailing, maneuvers and holds until completion. Conservative usable energy must remain above the R-002 reserve. No fixed duration or nonnegative daily energy balance is required. */
        comment notes /* The mission may finish with less stored energy than at departure. */
    }
    requirement def <'E-001'> EnergyAwareness {
        metadata workStatus : ModelingMetadata::StatusInfo { status = ModelingMetadata::StatusKind::open; }
        doc /*
         *  The vessel shall maintain conservative estimates of usable battery energy and the energy required for protected recovery. */
        comment conditions /* Energy estimation and conservative decision inputs; accuracy uses calibrated energy integration across operating battery temperatures. */
    }
    requirement def <'E-002'> NavigationAndControl {
        metadata workStatus : ModelingMetadata::StatusInfo { status = ModelingMetadata::StatusKind::open; }
        doc /* The vessel shall provide autonomous navigation and sail/steering control within the selected operational profile. */
        comment conditions /* Qualification uses the selected mission profile. Accuracy trials contain 1800 scheduled one-second epochs in 30 minutes; invalid or missing epochs count as failed epochs. Position and heading criteria use the same set of at least 1710 qualifying epochs, preventing separate selection of different good samples. Fault-injection runs are separate. */
    }
    requirement def <'E-003'> ResetRecovery {
        metadata workStatus : ModelingMetadata::StatusInfo { status = ModelingMetadata::StatusKind::open; }
        doc /* The vessel shall restore mode-appropriate autonomous operation after a watchdog reset. */
        comment conditions /* Watchdog-reset tests start above protected reserve with valid navigation observations. Normal sailing remains subject to N-035; data and qualification persistence have shared leaf criteria. */
    }
    requirement def <'E-004'> LowEnergyRecovery {
        metadata workStatus : ModelingMetadata::StatusInfo { status = ModelingMetadata::StatusKind::open; }
        doc /* The vessel shall protect essential functions when conservative usable energy reaches the recovery reserve. */
        comment conditions /* Reserve means R-002. Emergency/recovery cadence takes precedence; clearing low-energy state is independent of other modes, while payload enabling respects all restrictions. */
    }
    requirement def <'E-005'> Communications {
        metadata workStatus : ModelingMetadata::StatusInfo { status = ModelingMetadata::StatusKind::open; }
        doc /* The vessel shall retain telemetry through link outages for delivery after reconnection. */
        comment conditions /* Link availability is a delivery-test precondition, not a coverage guarantee. Normal, low-energy and recovery delivery cadence is 30 seconds, as allocated by GorgeChallenge::liveObservation. Outage tests last 24 hours. */
    }
    requirement def <'E-006'> IngressResponse {
        metadata workStatus : ModelingMetadata::StatusInfo { status = ModelingMetadata::StatusKind::open; }
        doc /* The vessel shall retain recoverability during the specified hull-ingress qualification. */
        comment conditions /* All leaves use a 30-minute freshwater injection at 10 mL/min into the normally dry hull. No pump technology is prescribed; R-004 remains applicable. */
    }
    requirement def <'E-007'> MissionEvidence {
        metadata workStatus : ModelingMetadata::StatusInfo { status = ModelingMetadata::StatusKind::open; }
        doc /* The vessel shall retain time-correlated mission evidence through communication and power interruptions. */
        comment conditions /* Periodic records contain position, heading, mode, gate progress, battery energy and fault state. Critical events are independent of periodic cadence. Timestamp accuracy is assessed with valid GNSS time. */
    }
    requirement roundTrip : RoundTrip;
    requirement multiDayEndurance : MultiDayEndurance;
    requirement energyAwareness : EnergyAwareness;
    requirement navigationAndControl : NavigationAndControl;
    requirement resetRecovery : ResetRecovery;
    requirement lowEnergyRecovery : LowEnergyRecovery;
    requirement communications : Communications;
    requirement ingressResponse : IngressResponse;
    requirement missionEvidence : MissionEvidence;

    #refinement dependency challengeCourse from roundTrip to GorgeChallenge::courseCompletion {
        metadata rationale : ModelingMetadata::Rationale { text = "Ordered gate crossings use the marker-referenced proposal in TransGorgeCourse; operational release remains subject to course review."; }
    }
    dependency challengeEndurance from multiDayEndurance to roundTrip {
        metadata rationale : ModelingMetadata::Rationale { text = "The complete finite round trip, including holding and contingency exposure, determines required endurance. Repeated circuits are a separate future objective. This is design motivation or an implementation choice, not a satisfaction implication."; }
    }
    dependency challengeAutonomy from navigationAndControl to GorgeChallenge::unassistedAttempt {
        metadata rationale : ModelingMetadata::Rationale { text = "The vessel needs onboard guidance and control to complete an unassisted attempt. This is design motivation or an implementation choice, not a satisfaction implication."; }
    }
    dependency challengePropulsion from roundTrip to GorgeChallenge::sailingPropulsion {
        metadata rationale : ModelingMetadata::Rationale { text = "Vehicle challenge operation excludes auxiliary motor propulsion; powered development tests are separate. This is design motivation or an implementation choice, not a satisfaction implication."; }
    }
    #refinement dependency challengeMonitoring from communications to GorgeChallenge::liveObservation {
        metadata rationale : ModelingMetadata::Rationale { text = "The vehicle telemetry requirement provides a more precise outage-retention and delivery specification for the observation aspect of C-005. Autonomous execution remains separately required."; }
    }
    dependency challengeOverride from communications to GorgeChallenge::emergencyIntervention {
        metadata rationale : ModelingMetadata::Rationale { text = "Vehicle communications provide emergency commands whose use ends attempt qualification. This is design motivation or an implementation choice, not a satisfaction implication."; }
    }

    // Derivations: direction is original requirement to derived requirement.
    dependency roundTripNavigation from navigationAndControl to roundTrip {
        metadata rationale : ModelingMetadata::Rationale { text = "Autonomous completion of the route needs observations, guidance, and actuation. This is design motivation or an implementation choice, not a satisfaction implication."; }
    }
    dependency roundTripReset from resetRecovery to roundTrip {
        metadata rationale : ModelingMetadata::Rationale { text = "A reset during an autonomous journey must not leave mission behavior undefined. This is design motivation or an implementation choice, not a satisfaction implication."; }
    }
    dependency roundTripCommunications from communications to roundTrip {
        metadata rationale : ModelingMetadata::Rationale { text = "Mission supervision and recovery need an agreed operator communication policy. This is design motivation or an implementation choice, not a satisfaction implication."; }
    }
    dependency roundTripIngress from ingressResponse to roundTrip {
        metadata rationale : ModelingMetadata::Rationale { text = "Recovering the boat after the journey motivates a defined response to small leaks. This is design motivation or an implementation choice, not a satisfaction implication."; }
    }
    dependency roundTripEvidence from missionEvidence to roundTrip {
        metadata rationale : ModelingMetadata::Rationale { text = "Assessing route completion and learning from the mission requires recorded evidence. This is design motivation or an implementation choice, not a satisfaction implication."; }
    }
    dependency enduranceEnergy from energyAwareness to multiDayEndurance {
        metadata rationale : ModelingMetadata::Rationale { text = "Multi-day operation with variable harvesting needs energy estimation and load management. This is design motivation or an implementation choice, not a satisfaction implication."; }
    }
    dependency enduranceLimpMode from lowEnergyRecovery to multiDayEndurance {
        metadata rationale : ModelingMetadata::Rationale { text = "Harvest shortfalls need an explicit degraded operating mode. This is design motivation or an implementation choice, not a satisfaction implication."; }
    }
    dependency energyLimpMode from lowEnergyRecovery to energyAwareness {
        metadata rationale : ModelingMetadata::Rationale { text = "Available-energy estimates and reserve policy must drive low-energy transitions. This is design motivation or an implementation choice, not a satisfaction implication."; }
    }

    requirement def <'P-001'> Transportability {
        metadata workStatus : ModelingMetadata::StatusInfo { status = ModelingMetadata::StatusKind::open; }
        doc /* The vessel shall support transport, assembly, launch and retrieval by one adult under the specified handling conditions. */
        comment conditions /* Demonstrate with one adult, no powered lift, a firm bank or ramp of slope at most 1:12, wind at most 5 m/s and waves at most 0.2 m. This is not a survival-envelope recovery claim. */
    }
    requirement transportability : Transportability;
    dependency deriveTransportability from transportability to BlueDog::DesignIntent {
        metadata rationale : ModelingMetadata::Rationale { text = "The owner requires one-person handling independently of either voyage outcome."; }
    }

    attribute printBuildLimit : LengthValue = 250 [mm];
    requirement def <'P-002'> DesktopManufacture {
        metadata workStatus : ModelingMetadata::StatusInfo { status = ModelingMetadata::StatusKind::open; }
        doc /* Every print job shall fit within positive X, Y and Z extents no greater than 250 mm each. */
        comment conditions /* Every printed component must be producible as one or more such jobs. The envelope includes the selected build orientation, supports, brim, raft and printer-required clearance. */
        attribute jobX : LengthValue;
        attribute jobY : LengthValue;
        attribute jobZ : LengthValue;
        attribute buildLimit : LengthValue = printBuildLimit;
        require constraint jobFits { PrintJobEnvelopeCriterion(jobX, jobY, jobZ, buildLimit) }
    }
    requirement desktopManufacture : DesktopManufacture;
    calc def PrintJobEnvelopeCriterion {
        in jobX : LengthValue;
        in jobY : LengthValue;
        in jobZ : LengthValue;
        in buildLimit : LengthValue;
        return verdict : Boolean;
        buildLimit > 0 [mm] and jobX > 0 [mm] and jobY > 0 [mm] and jobZ > 0 [mm] and
        jobX <= buildLimit and jobY <= buildLimit and jobZ <= buildLimit
    }
    dependency deriveDesktopManufacture from desktopManufacture to BlueDog::DesignIntent {
        metadata rationale : ModelingMetadata::Rationale { text = "The owner selected a 250 mm cubic desktop-printer build volume independently of mission completion."; }
    }

    requirement def <'P-003'> Serviceability {
        metadata workStatus : ModelingMetadata::StatusInfo { status = ModelingMetadata::StatusKind::open; }
        doc /* The vessel shall support replacement of serviceable equipment without structural damage. */
        comment conditions /* Exercise individual replacement of the battery, every electronics module, every actuator and every serviceable enclosure seal by one operator using hand tools. */
    }
    requirement serviceability : Serviceability;
    dependency deriveServiceability from serviceability to BlueDog::DesignIntent {
        metadata rationale : ModelingMetadata::Rationale { text = "Between-attempt serviceability is a project lifecycle constraint; it is not entailed by unassisted endurance."; }
    }

    requirement def <'S-001'> TrafficSafety {
        metadata workStatus : ModelingMetadata::StatusInfo { status = ModelingMetadata::StatusKind::open; }
        doc /* The vessel shall assess and respond to collision risks within reviewed class-specific detection and response envelopes while meeting the collision avoidance and nonimpediment obligations.*/
        metadata issue : ModelingMetadata::Issue { text = "BlueDogClassDetection defines the current class-specific allocation method. Numerical consequence, exposure, reliability, confidence and risk acceptance inputs remain unreviewed; hardware sensing and maneuver evidence is absent. Historical six-class 750 m analyses do not define the current requirement."; }
        comment conditions /* Use independently recorded head-on, crossing and overtaking AIS and non-AIS targets, day and night in the selected operational profile. Allocations shall include kinematic response distance, uncertainty, consequence-informed clearance and margins, and required timely observation and whole-response reliability with confidence criteria. Unreliably classified targets shall use a reviewed conservative envelope spanning plausible classes and occupant transitions. Collision avoidance and nonimpediment obligations remain unchanged.*/
    }
    requirement trafficSafety : TrafficSafety;
    #refinement dependency challengeTrafficResponse from BlueDogRequirements::trafficSafety to GorgeChallenge::trafficCoexistence {
        metadata workStatus : ModelingMetadata::StatusInfo { status = ModelingMetadata::StatusKind::open; }
        metadata rationale : ModelingMetadata::Rationale { text = "S-001 specifies observation, assessment and response supporting collision-free passage. Its reviewed performance envelopes are selected allocations; C-007 independently supplies navigation duties. No-contact outcome alone does not imply the assessment process."; }
    }
    dependency deriveTrafficSafety from trafficSafety to navigationAndControl {
        metadata rationale : ModelingMetadata::Rationale { text = "TrafficSafety supports navigationAndControl. This is design motivation or an implementation choice, not a satisfaction implication."; }
    }

    requirement def <'S-002'> OperatingBoundary {
        metadata workStatus : ModelingMetadata::StatusInfo { status = ModelingMetadata::StatusKind::open; }
        doc /* The vessel shall enforce the configured operating boundaries. */
        comment conditions /* Use uploaded permitted-water and exclusion polygons, with a 60-second prediction horizon. Inject approaches to every boundary, navigation loss and no-feasible-maneuver cases. Coordinates and uncertainty/clearance margins are controlled mission inputs with no default values. */
    }
    requirement operatingBoundary : OperatingBoundary;
    #refinement dependency challengeExclusions from operatingBoundary to GorgeChallenge::restrictedWaters {
        metadata rationale : ModelingMetadata::Rationale { text = "Configured polygons and predictive boundary handling refine the challenge exclusion obligation."; }
    }
    dependency deriveOperatingBoundary from operatingBoundary to roundTrip {
        metadata rationale : ModelingMetadata::Rationale { text = "OperatingBoundary supports roundTrip. This is design motivation or an implementation choice, not a satisfaction implication."; }
    }

    requirement def <'S-003'> EmergencyControl {
        metadata workStatus : ModelingMetadata::StatusInfo { status = ModelingMetadata::StatusKind::open; }
        doc /*
         *  The vessel shall preserve controlled emergency intervention through abort, local motor isolation and remote-control loss. */
        comment conditions /* Emergency intervention ends attempt qualification. Exercise abort, local isolation and remote-control loss with coexisting low-energy flags. S-110 through S-115 define the detailed acceptance criteria; powered shore-recovery capability is independently required by R-001. */
    }
    requirement emergencyControl : EmergencyControl;
    dependency deriveSafeRecovery from emergencyControl to GorgeChallenge::emergencyIntervention {
        metadata rationale : ModelingMetadata::Rationale { text = "Permitted emergency intervention requires explicit abort, qualification, isolation and control-loss behavior. This is design motivation or an implementation choice, not a satisfaction implication."; }
    }

    requirement def <'S-004'> NavigationConspicuity {
        metadata workStatus : ModelingMetadata::StatusInfo { status = ModelingMetadata::StatusKind::open; }
        doc /* The vessel shall present the navigation signals required for its operating mode. */
        comment conditions /* Use the deployment-specific compliance matrix for sailing, powered-recovery and stationary modes, including its visibility, arcs, colors and sound criteria. The matrix remains a deployment hold point under S-005. */
    }
    requirement navigationConspicuity : NavigationConspicuity;
    #refinement dependency challengeNavigationSignals from BlueDogRequirements::navigationConspicuity to GorgeChallenge::navigationRules {
        metadata workStatus : ModelingMetadata::StatusInfo { status = ModelingMetadata::StatusKind::open; }
        metadata rationale : ModelingMetadata::Rationale { text = "S-004 clarifies C-007 signal presentation during an attempt only. Its powered-recovery and stationary-mode coverage has the separate C-027 and deployment-matrix basis; those modes are not derived from attempt-only compliance."; }
    }
    dependency deriveNavigationConspicuity from navigationConspicuity to trafficSafety {
        metadata rationale : ModelingMetadata::Rationale { text = "NavigationConspicuity supports trafficSafety. This is design motivation or an implementation choice, not a satisfaction implication."; }
    }

    requirement def <'S-005'> RegulatoryClassification {
        metadata workStatus : ModelingMetadata::StatusInfo { status = ModelingMetadata::StatusKind::open; }
        doc /* Deployment shall require documented compliance with applicable navigation, radio and authorization obligations. */
        comment conditions /* Acceptance is deployment document review, not onboard behavior or an assertion of buoy status. */
    }
    requirement regulatoryClassification : RegulatoryClassification;
    dependency deriveRegulatoryClassification from regulatoryClassification to roundTrip {
        metadata rationale : ModelingMetadata::Rationale { text = "RegulatoryClassification supports roundTrip. This is design motivation or an implementation choice, not a satisfaction implication."; }
    }

    requirement def <'N-001'> EnvironmentalEnvelope {
        metadata workStatus : ModelingMetadata::StatusInfo { status = ModelingMetadata::StatusKind::open; }
        doc /* The vessel shall retain the functions required by its selected environmental profile and operating mode. */
        comment conditions /* Gorge qualification uses N-010; ocean qualification uses N-020. Both include applicable shared exposure requirements. Operational functions are navigation, sail/steering control, recording and available-link telemetry. Survival requires flotation, attached rig/ballast, dry electronics and retained mission state; course progress is not required. Required traffic assessment, navigation signals and available-link location reporting remain safety obligations in every mode. Loss of required safety capability invokes C-012 even when the structure survives. */
        comment notes /* Profiles are not interchangeable. Gorge release does not require ocean qualification, and Gorge success does not establish ocean capability. */
    }
    requirement environmentalEnvelope : EnvironmentalEnvelope;
    dependency deriveEnvironmentalEnvelope from environmentalEnvelope to roundTrip {
        metadata rationale : ModelingMetadata::Rationale { text = "EnvironmentalEnvelope supports roundTrip. This is design motivation or an implementation choice, not a satisfaction implication."; }
    }

    requirement def <'N-002'> MarineDurability {
        metadata workStatus : ModelingMetadata::StatusInfo { status = ModelingMetadata::StatusKind::open; }
        doc /* The vessel shall retain required function and structural integrity through its selected wet-exposure campaign. */
        comment conditions /* Gorge uses N-041 freshwater exposure; ocean uses N-042 saltwater exposure; dual-profile qualification requires both. Shared sealing, material-aging and thermal checks use the selected campaign. */
        comment notes /* A derivation does not make every mission-specific descendant applicable to every deployment. */
    }
    requirement marineDurability : MarineDurability;
    dependency deriveMarineDurability from marineDurability to environmentalEnvelope {
        metadata rationale : ModelingMetadata::Rationale { text = "MarineDurability supports environmentalEnvelope. This is design motivation or an implementation choice, not a satisfaction implication."; }
    }

    requirement def <'N-003'> CapsizeResilience {
        metadata workStatus : ModelingMetadata::StatusInfo { status = ModelingMetadata::StatusKind::open; }
        doc /*
         *  After the declared capsize disturbances, the vessel shall provide the recovery behavior defined for the selected righting or post-abort recovery strategy. */
        comment conditions /* Righting and upright control restoration apply to selected N-051/N-052 passive-righting criteria; C-018 independently permits post-abort limp recovery. No capsize waives required safety capability or motor inhibition. N-004 separately governs vegetation encounters. */

    }
    requirement capsizeResilience : CapsizeResilience;
    dependency deriveStabilityAndFouling from capsizeResilience to environmentalEnvelope {
        metadata rationale : ModelingMetadata::Rationale { text = "CapsizeResilience supports environmentalEnvelope. This dependency records design motivation rather than a satisfaction implication."; }
    }

    requirement def <'R-001'> RecoveryPropulsion {
        metadata workStatus : ModelingMetadata::StatusInfo { status = ModelingMetadata::StatusKind::open; }
        doc /* At maximum mission load, powered recovery shall reach a suitable shore retrieval location from the declared course recovery cases. */
        comment conditions /* Use route-specific wind, waves, current and casualty state, with installed propulsion performance. R-004 governs motor enable and challenge qualification; S-003 governs isolation and control loss. Course recovery scenarios must be accepted before qualification. */
        comment notes /* A sheltered thrust demonstration alone cannot qualify course-wide or capsized recovery. */
    }
    requirement recoveryPropulsion : RecoveryPropulsion;
    dependency deriveRecoveryPropulsion from recoveryPropulsion to GorgeChallenge::autonomousShoreRecovery {
        metadata rationale : ModelingMetadata::Rationale { text = "R-001 specifies the installed powered means supporting course-dependent shore recovery. Emergency-control acceptance remains a separate S-003 obligation."; }
    }

    calc def RecoveryReserveDemand {
        doc /* R-002 route-dependent reserve. Route traversal and recovery completion determine exposure durations; uncertainty is explicit. Powers are non-overlapping battery withdrawal rates. */
        in motorPower : PowerValue;
        in essentialPower : PowerValue;
        in poweredDuration : TimeValue;
        in essentialDuration : TimeValue;
        in uncertaintyFactor : Real;
        return reserve : EnergyValue;
        uncertaintyFactor * (motorPower * poweredDuration + essentialPower * essentialDuration)
    }

    requirement def <'R-002'> RecoveryEnergy {
        metadata workStatus : ModelingMetadata::StatusInfo { status = ModelingMetadata::StatusKind::open; }
        doc /* The protected reserve shall cover the energy required by a viable course-dependent shore recovery route with declared uncertainty allowance. */
        comment conditions /* Route evaluation supplies powered and essential durations from current position to a suitable retrieval location, including adverse current and final approach. Essential duration includes all powered transit. Powers use the installed configuration; uncertaintyFactor is at least one. An unavailable or infeasible recovery route cannot produce a valid reserve. */
        comment notes /* R-003 governs launch admission; E-004 governs in-mission reserve crossing. */
        attribute motorPower : PowerValue;
        attribute essentialPower : PowerValue;
        attribute reserveEnergy : EnergyValue;
        attribute poweredDuration : TimeValue;
        attribute essentialDuration : TimeValue;
        attribute uncertaintyFactor : Real;
        attribute routeFeasible : Boolean;
        require constraint reserveSizing {
            motorPower > 0 [W] and essentialPower > 0 [W] and
            routeFeasible and poweredDuration > 0 [s] and essentialDuration >= poweredDuration and uncertaintyFactor >= 1 and
            reserveEnergy >= RecoveryReserveDemand(motorPower, essentialPower, poweredDuration, essentialDuration, uncertaintyFactor)
        }
    }
    requirement recoveryEnergy : RecoveryEnergy;
    dependency deriveRecoveryEnergy from recoveryEnergy to recoveryPropulsion {
        metadata rationale : ModelingMetadata::Rationale { text = "RecoveryEnergy supports recoveryPropulsion. This is design motivation or an implementation choice, not a satisfaction implication."; }
    }

    requirement def <'C-101'> TelemetryEquipment {
        metadata workStatus : ModelingMetadata::StatusInfo { status = ModelingMetadata::StatusKind::open; }
        doc /* The shore endpoint shall present current vessel telemetry with explicit data age and identity. */
        comment conditions /* Freshness threshold is 120 seconds for normal, emergency, powered recovery or unknown mode, and 600 seconds only for explicitly reported low energy without emergency or powered recovery. Staleness describes data age, not diagnosed link failure. Exercise a 24-hour outage and reconnection. */
    }
    requirement telemetryEquipment : TelemetryEquipment;
    dependency deriveTelemetryEquipment from telemetryEquipment to communications {
        metadata rationale : ModelingMetadata::Rationale { text = "TelemetryEquipment supports communications. This is design motivation or an implementation choice, not a satisfaction implication."; }
    }

    requirement def <'C-102'> CommandIntegrity {
        metadata workStatus : ModelingMetadata::StatusInfo { status = ModelingMetadata::StatusKind::open; }
        doc /* The vessel shall accept external commands only under the specified authentication, freshness and qualification rules. */
        comment conditions /* Exercise complete command receipt, authentication failure, replayed sequence numbers, age greater than 30 seconds, and external control during a qualifying attempt. */
    }
    requirement commandIntegrity : CommandIntegrity;
    dependency deriveCommandIntegrity from commandIntegrity to communications {
        metadata rationale : ModelingMetadata::Rationale { text = "CommandIntegrity supports communications. This is design motivation or an implementation choice, not a satisfaction implication."; }
    }

    requirement def <'N-010'> GorgeEnvironment {
        metadata workStatus : ModelingMetadata::StatusInfo { status = ModelingMetadata::StatusKind::open; }
        doc /* The vessel shall operate in the freshwater Columbia River reach between Bingen and Stevenson, including opposing wind/current, short chop, traffic and submerged vegetation. */
        comment conditions /* Gorge-specific parameter limits and applicable shared exposure requirements apply together. */
        comment notes /* The profile excludes dam transit, ice and surf-zone launch. */
    }
    requirement gorgeEnvironment : GorgeEnvironment;
    dependency deriveGorgeEnvironment from gorgeEnvironment to roundTrip {
        metadata rationale : ModelingMetadata::Rationale { text = "The Gorge mission sets the river environment; it does not impose the ocean profile. This is design motivation or an implementation choice, not a satisfaction implication."; }
    }

    requirement def <'N-020'> OceanEnvironment {
        metadata applicability : BlueDogMissionScope::Applicability { mission = BlueDogMissionScope::MissionKind::futureOcean; }
        metadata workStatus : ModelingMetadata::StatusInfo { status = ModelingMetadata::StatusKind::open; }
        doc /* The vessel shall operate on a northeast Pacific passage toward Hawaii amid saltwater, ocean swell, wind seas and prolonged unattended exposure. */
        comment conditions /* Ocean-specific parameter limits and applicable shared exposure requirements apply together. */
        comment notes /* This baseline is neither a hurricane-survival claim nor completed route/season qualification. */
    }
    requirement oceanEnvironment : OceanEnvironment;
    dependency deriveOceanEnvironment from oceanEnvironment to BlueDog::Goals::hawaiiVoyage {
        metadata rationale : ModelingMetadata::Rationale { text = "The Hawaii mission sets the ocean environment; this profile is not a Gorge acceptance prerequisite. This is design motivation or an implementation choice, not a satisfaction implication."; }
    }

    requirement def <'N-011'> GorgeWind {
        metadata workStatus : ModelingMetadata::StatusInfo { status = ModelingMetadata::StatusKind::open; }
        doc /* The vessel shall retain operational functions in 0–15 m/s mean true wind with 3-second gusts up to 20 m/s. */
        comment conditions /* Operational functions are defined by N-001. Mean wind uses a 10-minute average referenced to 10 m above water. */
        comment notes /* Wind tolerance does not guarantee upstream progress. */
    }
    requirement gorgeWind : GorgeWind;
    #refinement dependency deriveGorgeWind from BlueDogRequirements::gorgeWind to BlueDogRequirements::gorgeEnvironment {
        metadata workStatus : ModelingMetadata::StatusInfo { status = ModelingMetadata::StatusKind::open; }
        metadata rationale : ModelingMetadata::Rationale { text = "N-011 specifies a detailed acceptance condition for N-010 within their stated applicability. Selected limits, mechanisms and campaign conditions remain independent allocations; refinement makes no satisfaction implication or automatic parent-coverage claim."; }
    }

    requirement def <'N-012'> GorgeWaves {
        metadata workStatus : ModelingMetadata::StatusInfo { status = ModelingMetadata::StatusKind::open; }
        doc /* The vessel shall retain operational functions in significant wave heights up to 1.5 m, peak periods 1.5–5 s and individual waves up to 3 m. */
        comment conditions /* N-001 defines operational functions. Wave statistics use 20-minute records. */
    }
    requirement gorgeWaves : GorgeWaves;
    #refinement dependency deriveGorgeWaves from BlueDogRequirements::gorgeWaves to BlueDogRequirements::gorgeEnvironment {
        metadata workStatus : ModelingMetadata::StatusInfo { status = ModelingMetadata::StatusKind::open; }
        metadata rationale : ModelingMetadata::Rationale { text = "N-012 specifies a detailed acceptance condition for N-010 within their stated applicability. Selected limits, mechanisms and campaign conditions remain independent allocations; refinement makes no satisfaction implication or automatic parent-coverage claim."; }
    }

    requirement def <'N-013'> GorgeCurrent {
        metadata workStatus : ModelingMetadata::StatusInfo { status = ModelingMetadata::StatusKind::open; }
        doc /* The vessel shall retain navigation and control in currents from 0 to 1.5 m/s from any direction relative to wind and waves. */
        comment conditions /* Predicted boundary risk invokes S-002. */
        comment notes /* Current tolerance does not guarantee progress or station keeping; positive upstream speed is not required at every wind speed or heading. */
    }
    requirement gorgeCurrent : GorgeCurrent;
    #refinement dependency deriveGorgeCurrent from BlueDogRequirements::gorgeCurrent to BlueDogRequirements::gorgeEnvironment {
        metadata workStatus : ModelingMetadata::StatusInfo { status = ModelingMetadata::StatusKind::open; }
        metadata rationale : ModelingMetadata::Rationale { text = "N-013 specifies a detailed acceptance condition for N-010 within their stated applicability. Selected limits, mechanisms and campaign conditions remain independent allocations; refinement makes no satisfaction implication or automatic parent-coverage claim."; }
    }

    requirement def <'N-014'> GorgeSurvivalWind {
        metadata workStatus : ModelingMetadata::StatusInfo { status = ModelingMetadata::StatusKind::open; }
        doc /* The vessel shall retain survival functions through the course-derived recovery exposure in mean wind up to 25 m/s and 3-second gusts up to 35 m/s. */
        comment conditions /* Use N-001 survival outcomes and the operational wind reference convention. Selected-profile wave, current, temperature and humidity limits apply concurrently. BlueDogEnvironmentReview::RecoveryExposureHours includes casualty transit and declared pickup delay. */
    }
    requirement gorgeSurvivalWind : GorgeSurvivalWind;
    #refinement dependency deriveGorgeSurvivalWind from BlueDogRequirements::gorgeSurvivalWind to BlueDogRequirements::gorgeEnvironment {
        metadata workStatus : ModelingMetadata::StatusInfo { status = ModelingMetadata::StatusKind::open; }
        metadata rationale : ModelingMetadata::Rationale { text = "N-014 specifies a detailed acceptance condition for N-010 within their stated applicability. Selected limits, mechanisms and campaign conditions remain independent allocations; refinement makes no satisfaction implication or automatic parent-coverage claim."; }
    }

    requirement def <'N-015'> GorgeSurvivalWaves {
        metadata workStatus : ModelingMetadata::StatusInfo { status = ModelingMetadata::StatusKind::open; }
        doc /* The vessel shall retain survival functions through the course-derived recovery exposure in significant wave heights up to 2 m, peak periods 1.5–7 s and individual waves up to 4 m. */
        comment conditions /* N-001 defines survival outcomes. */
    }
    requirement gorgeSurvivalWaves : GorgeSurvivalWaves;
    #refinement dependency deriveGorgeSurvivalWaves from BlueDogRequirements::gorgeSurvivalWaves to BlueDogRequirements::gorgeEnvironment {
        metadata workStatus : ModelingMetadata::StatusInfo { status = ModelingMetadata::StatusKind::open; }
        metadata rationale : ModelingMetadata::Rationale { text = "N-015 specifies a detailed acceptance condition for N-010 within their stated applicability. Selected limits, mechanisms and campaign conditions remain independent allocations; refinement makes no satisfaction implication or automatic parent-coverage claim."; }
    }

    requirement def <'N-021'> OceanWind {
        metadata applicability : BlueDogMissionScope::Applicability { mission = BlueDogMissionScope::MissionKind::futureOcean; }
        metadata workStatus : ModelingMetadata::StatusInfo { status = ModelingMetadata::StatusKind::open; }
        doc /* The vessel shall retain operational functions in 3–15 m/s mean true wind with 3-second gusts up to 20 m/s. */
        comment conditions /* Operational functions are defined by N-001. Mean wind uses a 10-minute average referenced to 10 m above water. */
        comment notes /* Wind tolerance does not guarantee upstream progress. */
    }
    requirement oceanWind : OceanWind;
    #refinement dependency deriveOceanWind from BlueDogRequirements::oceanWind to BlueDogRequirements::oceanEnvironment {
        metadata workStatus : ModelingMetadata::StatusInfo { status = ModelingMetadata::StatusKind::open; }
        metadata rationale : ModelingMetadata::Rationale { text = "N-021 specifies a detailed acceptance condition for N-020 within their stated applicability. Selected limits, mechanisms and campaign conditions remain independent allocations; refinement makes no satisfaction implication or automatic parent-coverage claim."; }
    }

    requirement def <'N-022'> OceanWaves {
        metadata applicability : BlueDogMissionScope::Applicability { mission = BlueDogMissionScope::MissionKind::futureOcean; }
        metadata workStatus : ModelingMetadata::StatusInfo { status = ModelingMetadata::StatusKind::open; }
        doc /* The vessel shall retain operational functions in significant wave heights up to 3 m, peak periods 5–20 s and individual waves up to 6 m. */
        comment conditions /* N-001 defines operational functions. Wave statistics use 20-minute records. */
    }
    requirement oceanWaves : OceanWaves;
    #refinement dependency deriveOceanWaves from BlueDogRequirements::oceanWaves to BlueDogRequirements::oceanEnvironment {
        metadata workStatus : ModelingMetadata::StatusInfo { status = ModelingMetadata::StatusKind::open; }
        metadata rationale : ModelingMetadata::Rationale { text = "N-022 specifies a detailed acceptance condition for N-020 within their stated applicability. Selected limits, mechanisms and campaign conditions remain independent allocations; refinement makes no satisfaction implication or automatic parent-coverage claim."; }
    }

    requirement def <'N-023'> OceanCurrent {
        metadata applicability : BlueDogMissionScope::Applicability { mission = BlueDogMissionScope::MissionKind::futureOcean; }
        metadata workStatus : ModelingMetadata::StatusInfo { status = ModelingMetadata::StatusKind::open; }
        doc /* The vessel shall retain navigation and control in currents from 0 to 1.0 m/s from any direction relative to wind and waves. */
        comment conditions /* Predicted boundary risk invokes S-002. */
        comment notes /* Current tolerance does not guarantee progress or station keeping; positive upstream speed is not required at every wind speed or heading. */
    }
    requirement oceanCurrent : OceanCurrent;
    #refinement dependency deriveOceanCurrent from BlueDogRequirements::oceanCurrent to BlueDogRequirements::oceanEnvironment {
        metadata workStatus : ModelingMetadata::StatusInfo { status = ModelingMetadata::StatusKind::open; }
        metadata rationale : ModelingMetadata::Rationale { text = "N-023 specifies a detailed acceptance condition for N-020 within their stated applicability. Selected limits, mechanisms and campaign conditions remain independent allocations; refinement makes no satisfaction implication or automatic parent-coverage claim."; }
    }

    requirement def <'N-024'> OceanSurvivalWind {
        metadata applicability : BlueDogMissionScope::Applicability { mission = BlueDogMissionScope::MissionKind::futureOcean; }
        metadata workStatus : ModelingMetadata::StatusInfo { status = ModelingMetadata::StatusKind::open; }
        doc /* The vessel shall retain survival functions for 24 continuous hours in mean wind up to 25 m/s and 3-second gusts up to 35 m/s. */
        comment conditions /* Use N-001 survival outcomes and the operational wind reference convention. Selected-profile wave, current, temperature and humidity limits apply concurrently. */
    }
    requirement oceanSurvivalWind : OceanSurvivalWind;
    #refinement dependency deriveOceanSurvivalWind from BlueDogRequirements::oceanSurvivalWind to BlueDogRequirements::oceanEnvironment {
        metadata workStatus : ModelingMetadata::StatusInfo { status = ModelingMetadata::StatusKind::open; }
        metadata rationale : ModelingMetadata::Rationale { text = "N-024 specifies a detailed acceptance condition for N-020 within their stated applicability. Selected limits, mechanisms and campaign conditions remain independent allocations; refinement makes no satisfaction implication or automatic parent-coverage claim."; }
    }

    requirement def <'N-025'> OceanSurvivalWaves {
        metadata applicability : BlueDogMissionScope::Applicability { mission = BlueDogMissionScope::MissionKind::futureOcean; }
        metadata workStatus : ModelingMetadata::StatusInfo { status = ModelingMetadata::StatusKind::open; }
        doc /* The vessel shall retain survival functions for 24 continuous hours in significant wave heights up to 6 m, peak periods 6–20 s and individual waves up to 12 m. */
        comment conditions /* N-001 defines survival outcomes. */
    }
    requirement oceanSurvivalWaves : OceanSurvivalWaves;
    #refinement dependency deriveOceanSurvivalWaves from BlueDogRequirements::oceanSurvivalWaves to BlueDogRequirements::oceanEnvironment {
        metadata workStatus : ModelingMetadata::StatusInfo { status = ModelingMetadata::StatusKind::open; }
        metadata rationale : ModelingMetadata::Rationale { text = "N-025 specifies a detailed acceptance condition for N-020 within their stated applicability. Selected limits, mechanisms and campaign conditions remain independent allocations; refinement makes no satisfaction implication or automatic parent-coverage claim."; }
    }

    requirement def <'N-030'> AirTemperature {
        metadata workStatus : ModelingMetadata::StatusInfo { status = ModelingMetadata::StatusKind::open; }
        doc /* The vessel shall retain mode-appropriate functions at ambient air temperatures from 0 to 40 degC. */
        comment conditions /* N-001/N-035 define operational and survival functions. */
    }
    requirement airTemperature : AirTemperature;
    #refinement dependency deriveAirTemperature from BlueDogRequirements::airTemperature to BlueDogRequirements::environmentalEnvelope {
        metadata workStatus : ModelingMetadata::StatusInfo { status = ModelingMetadata::StatusKind::open; }
        metadata rationale : ModelingMetadata::Rationale { text = "N-030 specifies a detailed acceptance condition for N-001 within their stated applicability. Selected limits, mechanisms and campaign conditions remain independent allocations; refinement makes no satisfaction implication or automatic parent-coverage claim."; }
    }

    requirement def <'N-031'> WaterTemperature {
        metadata workStatus : ModelingMetadata::StatusInfo { status = ModelingMetadata::StatusKind::open; }
        doc /* Immersed hull, appendages and equipment shall retain mode-appropriate functions in water from 2 to 30 degC. */
        comment conditions /* N-001/N-035 define operational and survival functions. */
    }
    requirement waterTemperature : WaterTemperature;
    #refinement dependency deriveWaterTemperature from BlueDogRequirements::waterTemperature to BlueDogRequirements::environmentalEnvelope {
        metadata workStatus : ModelingMetadata::StatusInfo { status = ModelingMetadata::StatusKind::open; }
        metadata rationale : ModelingMetadata::Rationale { text = "N-031 specifies a detailed acceptance condition for N-001 within their stated applicability. Selected limits, mechanisms and campaign conditions remain independent allocations; refinement makes no satisfaction implication or automatic parent-coverage claim."; }
    }

    requirement def <'N-032'> Humidity {
        metadata workStatus : ModelingMetadata::StatusInfo { status = ModelingMetadata::StatusKind::open; }
        doc /* Installed equipment shall retain operational functions at 0–100 percent relative humidity, including condensation. */
    }
    requirement humidity : Humidity;
    #refinement dependency deriveHumidity from BlueDogRequirements::humidity to BlueDogRequirements::environmentalEnvelope {
        metadata workStatus : ModelingMetadata::StatusInfo { status = ModelingMetadata::StatusKind::open; }
        metadata rationale : ModelingMetadata::Rationale { text = "N-032 specifies a detailed acceptance condition for N-001 within their stated applicability. Selected limits, mechanisms and campaign conditions remain independent allocations; refinement makes no satisfaction implication or automatic parent-coverage claim."; }
    }

    requirement def <'N-033'> Visibility {
        metadata workStatus : ModelingMetadata::StatusInfo { status = ModelingMetadata::StatusKind::open; }
        doc /* The vessel shall provide mode-appropriate navigation and traffic response across the specified visibility conditions. */
        comment conditions /* Exercise daylight and darkness at meteorological visibility of at least 1 km, and detected visibility below 1 km. Apply current BlueDogClassDetection class-specific or conservative plausible-class envelopes and the S-001 reviewed observation and response criteria.*/
    }
    requirement visibility : Visibility;
    #refinement dependency deriveVisibility from BlueDogRequirements::visibility to BlueDogRequirements::environmentalEnvelope {
        metadata workStatus : ModelingMetadata::StatusInfo { status = ModelingMetadata::StatusKind::open; }
        metadata rationale : ModelingMetadata::Rationale { text = "N-033 specifies a detailed acceptance condition for N-001 within their stated applicability. Selected limits, mechanisms and campaign conditions remain independent allocations; refinement makes no satisfaction implication or automatic parent-coverage claim."; }
    }

    requirement def <'N-034'> CalmOperation {
        metadata workStatus : ModelingMetadata::StatusInfo { status = ModelingMetadata::StatusKind::open; }
        doc /* While waiting in mean wind below 3 m/s, the vessel shall preserve the course-derived recovery reserve. */
        comment conditions /* Calm-mode functions are navigation, recording and autonomous boundary/traffic contingency. Waiting may continue only while forecast coverage, traffic/boundary safety and measured calm-mode loads preserve route-dependent recovery authority; no fixed waiting endurance is imposed. Autonomous safety recovery first terminates qualification under GorgeChallenge::safetyCapabilityAbort, then may enable the motor under R-004. */
        comment notes /* Neither progress nor station keeping is required. */
    }
    requirement calmOperation : CalmOperation;
    #refinement dependency deriveCalmOperation from BlueDogRequirements::calmOperation to BlueDogRequirements::environmentalEnvelope {
        metadata workStatus : ModelingMetadata::StatusInfo { status = ModelingMetadata::StatusKind::open; }
        metadata rationale : ModelingMetadata::Rationale { text = "N-034 specifies a detailed acceptance condition for N-001 within their stated applicability. Selected limits, mechanisms and campaign conditions remain independent allocations; refinement makes no satisfaction implication or automatic parent-coverage claim."; }
    }

    requirement def <'N-035'> EnvelopeTransition {
        metadata workStatus : ModelingMetadata::StatusInfo { status = ModelingMetadata::StatusKind::open; }
        doc /* The vessel shall select survival or sailing operation according to the defined environmental transition conditions. */
        comment conditions /* The trigger is a detected upper operational wind or wave limit exceedance for the selected profile; calm invokes N-034. Resumption eligibility requires 10 continuous minutes inside the selected wind/wave limits, valid navigation, upright control, preserved required safety capability and no low-energy, emergency-recovery or isolation restriction. Resuming a control mode never clears a disqualified attempt. */
    }
    requirement envelopeTransition : EnvelopeTransition;
    #refinement dependency deriveEnvelopeTransition from BlueDogRequirements::envelopeTransition to BlueDogRequirements::environmentalEnvelope {
        metadata workStatus : ModelingMetadata::StatusInfo { status = ModelingMetadata::StatusKind::open; }
        metadata rationale : ModelingMetadata::Rationale { text = "N-035 specifies a detailed acceptance condition for N-001 within their stated applicability. Selected limits, mechanisms and campaign conditions remain independent allocations; refinement makes no satisfaction implication or automatic parent-coverage claim."; }
    }

    requirement def <'N-041'> FreshwaterExposure {
        metadata workStatus : ModelingMetadata::StatusInfo { status = ModelingMetadata::StatusKind::open; }
        doc /* For Gorge qualification, following continuous freshwater exposure for the full declared mission history, with submerged parts continuously wet and complete topside spray wetting at least once per hour, the vessel shall pass its Gorge functional checks without repair or servicing. */
    }
    requirement freshwaterExposure : FreshwaterExposure;
    #refinement dependency deriveFreshwaterExposure from BlueDogRequirements::freshwaterExposure to BlueDogRequirements::marineDurability {
        metadata workStatus : ModelingMetadata::StatusInfo { status = ModelingMetadata::StatusKind::open; }
        metadata rationale : ModelingMetadata::Rationale { text = "N-041 specifies a detailed acceptance condition for N-002 within their stated applicability. Selected limits, mechanisms and campaign conditions remain independent allocations; refinement makes no satisfaction implication or automatic parent-coverage claim."; }
    }

    requirement def <'N-042'> SaltwaterExposure {
        metadata applicability : BlueDogMissionScope::Applicability { mission = BlueDogMissionScope::MissionKind::futureOcean; }
        metadata workStatus : ModelingMetadata::StatusInfo { status = ModelingMetadata::StatusKind::open; }
        doc /* For ocean qualification, following 30 days continuous 35 g/kg saltwater exposure, with submerged parts continuously wet and complete topside spray wetting at least once per hour, the vessel shall pass its ocean functional checks without repair or servicing. */
        comment notes /* The exposure campaign does not establish the eventual passage duration. */
    }
    requirement saltwaterExposure : SaltwaterExposure;

    requirement def <'N-043'> EnclosureSealing {
        metadata workStatus : ModelingMetadata::StatusInfo { status = ModelingMetadata::StatusKind::open; }
        doc /* Before and after each wet-exposure campaign, installed electronics enclosures, connectors and penetrations shall show no detectable liquid ingress on dry internal water-sensitive indicators after 30 minutes immersion with their highest point 1 m below the water surface. */
    }
    requirement enclosureSealing : EnclosureSealing;
    #refinement dependency deriveEnclosureSealing from BlueDogRequirements::enclosureSealing to BlueDogRequirements::marineDurability {
        metadata workStatus : ModelingMetadata::StatusInfo { status = ModelingMetadata::StatusKind::open; }
        metadata rationale : ModelingMetadata::Rationale { text = "N-043 specifies a detailed acceptance condition for N-002 within their stated applicability. Selected limits, mechanisms and campaign conditions remain independent allocations; refinement makes no satisfaction implication or automatic parent-coverage claim."; }
    }

    requirement def <'N-044'> WetMechanicalIntegrity {
        metadata workStatus : ModelingMetadata::StatusInfo { status = ModelingMetadata::StatusKind::open; }
        doc /* External mechanisms and structural joints shall retain integrity after the selected wet-exposure campaign. */
        comment conditions /* Evaluate after each selected profile wet-exposure campaign under N-002. */
    }
    requirement wetMechanicalIntegrity : WetMechanicalIntegrity;
    #refinement dependency deriveWetMechanicalIntegrity from BlueDogRequirements::wetMechanicalIntegrity to BlueDogRequirements::marineDurability {
        metadata workStatus : ModelingMetadata::StatusInfo { status = ModelingMetadata::StatusKind::open; }
        metadata rationale : ModelingMetadata::Rationale { text = "N-044 specifies a detailed acceptance condition for N-002 within their stated applicability. Selected limits, mechanisms and campaign conditions remain independent allocations; refinement makes no satisfaction implication or automatic parent-coverage claim."; }
    }

    requirement def <'N-045'> WetElectricalIntegrity {
        metadata workStatus : ModelingMetadata::StatusInfo { status = ModelingMetadata::StatusKind::open; }
        doc /* Cable assemblies shall retain electrical integrity after the selected wet-exposure campaign. */
        comment conditions /* Evaluate disconnected cable assemblies after each selected profile wet-exposure campaign under N-002; disconnect electronics for insulation measurement. */
    }
    requirement wetElectricalIntegrity : WetElectricalIntegrity;
    #refinement dependency deriveWetElectricalIntegrity from BlueDogRequirements::wetElectricalIntegrity to BlueDogRequirements::marineDurability {
        metadata workStatus : ModelingMetadata::StatusInfo { status = ModelingMetadata::StatusKind::open; }
        metadata rationale : ModelingMetadata::Rationale { text = "N-045 specifies a detailed acceptance condition for N-002 within their stated applicability. Selected limits, mechanisms and campaign conditions remain independent allocations; refinement makes no satisfaction implication or automatic parent-coverage claim."; }
    }

    requirement def <'N-046'> SolarHeating {
        metadata workStatus : ModelingMetadata::StatusInfo { status = ModelingMetadata::StatusKind::open; }
        doc /* The vessel shall retain safe powered operation during the specified solar-heating exposure. */
        comment conditions /* Expose the powered vessel to 40 degC ambient air and 1000 W/m2 incident solar irradiance for 8 hours; use the installed battery manufacturer temperature limits. */
    }
    requirement solarHeating : SolarHeating;
    #refinement dependency deriveSolarHeating from BlueDogRequirements::solarHeating to BlueDogRequirements::marineDurability {
        metadata workStatus : ModelingMetadata::StatusInfo { status = ModelingMetadata::StatusKind::open; }
        metadata rationale : ModelingMetadata::Rationale { text = "N-046 specifies a detailed acceptance condition for N-002 within their stated applicability. Selected limits, mechanisms and campaign conditions remain independent allocations; refinement makes no satisfaction implication or automatic parent-coverage claim."; }
    }

    requirement def <'N-047'> PrintedMaterialAging {
        metadata workStatus : ModelingMetadata::StatusInfo { status = ModelingMetadata::StatusKind::open; }
        doc /* Aged printed structural components shall retain the load capacity credited to them in the qualified design. */
        comment conditions /* Use exposure representative of the selected mission and intended service interval, followed by N-041 for Gorge or N-042 for ocean. Establish aged directional load bounds for the actual print and joints. The initial 300 MJ/m2 UV dose is a provisional accelerated-test condition, not a mission-derived dose; compare aged capacity with credited demand, not an arbitrary percentage of unaged strength. */
        attribute creditedLoadCapacityN : Real;
        attribute qualifiedAgedCapacityN : Real;
        attribute exposureEvidenceAccepted : Boolean;
        require constraint acceptance { exposureEvidenceAccepted and creditedLoadCapacityN > 0 and qualifiedAgedCapacityN >= creditedLoadCapacityN }
    }
    requirement printedMaterialAging : PrintedMaterialAging;
    #refinement dependency derivePrintedMaterialAging from BlueDogRequirements::printedMaterialAging to BlueDogRequirements::marineDurability {
        metadata workStatus : ModelingMetadata::StatusInfo { status = ModelingMetadata::StatusKind::open; }
        metadata rationale : ModelingMetadata::Rationale { text = "N-047 specifies a detailed acceptance condition for N-002 within their stated applicability. Selected limits, mechanisms and campaign conditions remain independent allocations; refinement makes no satisfaction implication or automatic parent-coverage claim."; }
    }

    requirement def <'N-051'> SelfRighting {
        metadata workStatus : ModelingMetadata::StatusInfo { status = ModelingMetadata::StatusKind::open; }
        doc /* The vessel shall recover from the specified capsize releases without external assistance or motor thrust. */
        comment conditions /* Apply to the selected passive-righting concept, not every challenge-compliant vessel. Use minimum and maximum mission loading, five releases at each angle of 90 and 180 degrees toward each side, without external action or motor thrust. Use freshwater for Gorge or 35 g/kg saltwater for ocean; dual qualification requires both media. N-118 RightingDeadline, N-119 CapsizeRigRetention, N-120 CapsizeBallastRetention and N-121 CapsizeElectronicsSealing apply to every release. */
    }
    requirement selfRighting : SelfRighting;
    dependency selectedRightingStrategy from selfRighting to capsizeResilience {
        metadata rationale : ModelingMetadata::Rationale { text = "Passive self-righting is the current monohull design strategy, not entailed by the challenge. C-018 also permits demonstrated limp recovery after abort; an alternative concept may meet that obligation without self-righting."; }
    }

    requirement def <'N-052'> CapsizeControlRecovery {
        metadata workStatus : ModelingMetadata::StatusInfo { status = ModelingMetadata::StatusKind::open; }
        doc /* The vessel shall restore mode-appropriate control after each specified capsize release. */
        comment conditions /* Apply to every N-051 release without operator input. Mode-appropriate control does not mean normal sailing before the N-035 resumption gate permits it. */
    }
    requirement capsizeControlRecovery : CapsizeControlRecovery;
    dependency deriveCapsizeControlRecovery from capsizeControlRecovery to capsizeResilience {
        metadata rationale : ModelingMetadata::Rationale { text = "Upright control restoration is an obligation of the selected passive-righting strategy. Alternative challenge concepts may provide post-abort limp recovery without this strategy."; }
    }

    requirement def <'N-053'> SubmergedWeedPassage {
        metadata workStatus : ModelingMetadata::StatusInfo { status = ModelingMetadata::StatusKind::open; }
        doc /* The vessel shall tolerate submerged milfoil-like vegetation during the specified unassisted Gorge sailing passes. */
        comment conditions /* Gorge campaign: five consecutive sailing passes without manual clearing or motor use through a 5 m by 1 m patch of 20 flexible branched stems per square metre, each 0.5-1.0 m long, extending from below the deepest appendage to within 0.1 m of the surface. Use 5 m/s mean wind and the weed-free reference heading. Record material, branch geometry, wet bending stiffness and anchoring. */
        metadata issue : ModelingMetadata::Issue { text = "Equivalence of the vegetation surrogate to local milfoil requires physical-test validation."; }
    }
    requirement submergedWeedPassage : SubmergedWeedPassage;
    #refinement dependency deriveSubmergedWeedPassage from BlueDogRequirements::submergedWeedPassage to BlueDogRequirements::vegetationResilience {
        metadata workStatus : ModelingMetadata::StatusInfo { status = ModelingMetadata::StatusKind::open; }
        metadata rationale : ModelingMetadata::Rationale { text = "N-053 specifies a detailed acceptance condition for N-004 within their stated applicability. Selected limits, mechanisms and campaign conditions remain independent allocations; refinement makes no satisfaction implication or automatic parent-coverage claim."; }
    }

    requirement def <'N-054'> WeedSnagShedding {
        metadata workStatus : ModelingMetadata::StatusInfo { status = ModelingMetadata::StatusKind::open; }
        doc /* The vessel shall recover sailing performance after the specified appendage weed snags without assistance or motor use. */
        comment conditions /* Gorge campaign: drape one wet 1 m branched stem over one appendage leading edge at a time, five repetitions per appendage, with N-053 surrogate characteristics, 5 m/s mean wind and the unobstructed reference heading. No manual assistance or motor use. N-128 WeedSnagSpeedRecovery and N-129 WeedSnagSteeringRecovery apply to every repetition; visible stem removal alone is insufficient. */
    }
    requirement weedSnagShedding : WeedSnagShedding;
    #refinement dependency deriveWeedSnagShedding from BlueDogRequirements::weedSnagShedding to BlueDogRequirements::vegetationResilience {
        metadata workStatus : ModelingMetadata::StatusInfo { status = ModelingMetadata::StatusKind::open; }
        metadata rationale : ModelingMetadata::Rationale { text = "N-054 specifies a detailed acceptance condition for N-004 within their stated applicability. Selected limits, mechanisms and campaign conditions remain independent allocations; refinement makes no satisfaction implication or automatic parent-coverage claim."; }
    }

    requirement def <'N-055'> WeedBlockageResponse {
        metadata workStatus : ModelingMetadata::StatusInfo { status = ModelingMetadata::StatusKind::open; }
        doc /* The vessel shall enter autonomous fouling contingency when the defined weed-blockage trigger occurs. */
        comment conditions /* Gorge trigger: vegetation prevents completion of commanded rudder motion for 5 seconds, or keeps water-relative speed below 25 percent of the preceding weed-free 60-second mean for 60 seconds with mean wind at least 3 m/s. Dense mats are a blockage/avoidance case, not a pass-through claim. */
    }
    requirement weedBlockageResponse : WeedBlockageResponse;
    #refinement dependency deriveWeedBlockageResponse from BlueDogRequirements::weedBlockageResponse to BlueDogRequirements::vegetationResilience {
        metadata workStatus : ModelingMetadata::StatusInfo { status = ModelingMetadata::StatusKind::open; }
        metadata rationale : ModelingMetadata::Rationale { text = "N-055 specifies a detailed acceptance condition for N-004 within their stated applicability. Selected limits, mechanisms and campaign conditions remain independent allocations; refinement makes no satisfaction implication or automatic parent-coverage claim."; }
    }

    requirement def <'N-056'> RecoveryPropulsorWeeds {
        metadata workStatus : ModelingMetadata::StatusInfo { status = ModelingMetadata::StatusKind::open; }
        doc /* The recovery propulsion system shall tolerate the specified weed encounters within its rated electrical and thermal limits. */
        comment conditions /* Use a separately designated Gorge powered-recovery test with five passes through the N-053 patch without manual propulsor clearing, on the weed-free powered reference heading. Exercise locked propulsor separately. */
    }
    requirement recoveryPropulsorWeeds : RecoveryPropulsorWeeds;
    #refinement dependency deriveRecoveryPropulsorWeeds from BlueDogRequirements::recoveryPropulsorWeeds to BlueDogRequirements::vegetationResilience {
        metadata workStatus : ModelingMetadata::StatusInfo { status = ModelingMetadata::StatusKind::open; }
        metadata rationale : ModelingMetadata::Rationale { text = "N-056 specifies a detailed acceptance condition for N-004 within their stated applicability. Selected limits, mechanisms and campaign conditions remain independent allocations; refinement makes no satisfaction implication or automatic parent-coverage claim."; }
    }
    dependency motorWeedTolerance from recoveryPropulsorWeeds to recoveryPropulsion {
        metadata rationale : ModelingMetadata::Rationale { text = "The recovery propulsor must remain usable in the vegetation encountered by the sailing vessel. This is design motivation or an implementation choice, not a satisfaction implication."; }
    }
    requirement def <'E-008'> NavigationAvailability {
        metadata workStatus : ModelingMetadata::StatusInfo { status = ModelingMetadata::StatusKind::open; }
        doc /* The vessel shall maintain valid navigation inputs and reject stale observations. */
        comment conditions /* Campaigns use 1800 scheduled one-second epochs in 30 minutes, with missing/invalid epochs counted as failures. Fault injection is separate. */
    }
    requirement navigationAvailability : NavigationAvailability;
    requirement def <'R-003'> LaunchEnergyAdmission {
        metadata workStatus : ModelingMetadata::StatusInfo { status = ModelingMetadata::StatusKind::open; }
        doc /*
         *  The vessel shall inhibit mission start unless a valid usable-energy estimate no older than 1 second strictly exceeds a valid R-002 protected reserve. */
        comment conditions /* Missing, stale or invalid estimates or reserve configuration inhibit start. */
        attribute conservativeStartEnergy : EnergyValue;
        attribute protectedReserve : EnergyValue;
        attribute estimateAge : TimeValue;
        attribute estimateValid : Boolean;
        attribute reserveValid : Boolean;
        attribute missionStartEnabled : Boolean;
        attribute admissionEligible : Boolean =
            estimateValid and reserveValid and protectedReserve > 0 [J] and
        estimateAge >= 0 [s] and estimateAge <= 1 [s] and
        conservativeStartEnergy > protectedReserve;
        require constraint launchEnergyGate {
            not missionStartEnabled or admissionEligible
        }
    }
    requirement launchEnergyAdmission : LaunchEnergyAdmission;
    requirement def <'R-004'> ChallengeMotorInhibition {
        metadata workStatus : ModelingMetadata::StatusInfo { status = ModelingMetadata::StatusKind::open; }
        doc /*
         *  The vessel shall inhibit motor thrust until it has durably recorded a known nonqualifying status for the attempt. */
        comment conditions /* Exercise qualifying, nonqualifying and unknown qualification states, restart, link loss, power loss during transitions and conflicting/stale commands. Shared qualification persistence applies before enabling intervention. */
    }
    requirement challengeMotorInhibition : ChallengeMotorInhibition;
    #refinement dependency auditDerivation1 from BlueDogRequirements::navigationAvailability to BlueDogRequirements::navigationAndControl {
        metadata workStatus : ModelingMetadata::StatusInfo { status = ModelingMetadata::StatusKind::open; }
        metadata rationale : ModelingMetadata::Rationale { text = "E-008 specifies a detailed acceptance condition for E-002 within their stated applicability. Selected limits, mechanisms and campaign conditions remain independent allocations; refinement makes no satisfaction implication or automatic parent-coverage claim."; }
    }
    dependency auditDerivation2 from launchEnergyAdmission to recoveryEnergy {
        metadata rationale : ModelingMetadata::Rationale { text = "The selected launch gate consumes the route-dependent reserve calculation. A changed reserve or validity rule requires admission review; the reserve magnitude alone does not define launch behavior."; }
    }
    dependency auditDerivation3 from challengeMotorInhibition to GorgeChallenge::sailingPropulsion {
        metadata rationale : ModelingMetadata::Rationale { text = "The onboard interlock is the selected enforcement of sail-only qualification. The challenge rule governs the attempt outcome without mandating this particular interlock design."; }
    }
    dependency auditDerivation4 from challengeMotorInhibition to GorgeChallenge::unassistedAttempt {
        metadata rationale : ModelingMetadata::Rationale { text = "No-intervention qualification must survive resets and motor-mode transitions. This is design motivation or an implementation choice, not a satisfaction implication."; }
    }
    dependency auditDerivation5 from commandIntegrity to GorgeChallenge::unassistedAttempt {
        metadata rationale : ModelingMetadata::Rationale { text = "Accepted external control changes the attempt qualification; communications alone does not supply this rule. This is design motivation or an implementation choice, not a satisfaction implication."; }
    }
    dependency auditDerivation6 from commandIntegrity to GorgeChallenge::emergencyIntervention {
        metadata rationale : ModelingMetadata::Rationale { text = "The emergency control channel needs authenticated, fresh commands and persistent qualification changes. This is design motivation or an implementation choice, not a satisfaction implication."; }
    }
    #refinement dependency auditDerivation10 from BlueDogRequirements::freshwaterExposure to BlueDogRequirements::gorgeEnvironment {
        metadata workStatus : ModelingMetadata::StatusInfo { status = ModelingMetadata::StatusKind::open; }
        metadata rationale : ModelingMetadata::Rationale { text = "N-041 specifies a detailed acceptance condition for N-010 within their stated applicability. Selected limits, mechanisms and campaign conditions remain independent allocations; refinement makes no satisfaction implication or automatic parent-coverage claim."; }
    }
    #refinement dependency auditDerivation11 from BlueDogRequirements::saltwaterExposure to BlueDogRequirements::oceanEnvironment {
        metadata workStatus : ModelingMetadata::StatusInfo { status = ModelingMetadata::StatusKind::open; }
        metadata rationale : ModelingMetadata::Rationale { text = "N-042 specifies a detailed acceptance condition for N-020 within their stated applicability. Selected limits, mechanisms and campaign conditions remain independent allocations; refinement makes no satisfaction implication or automatic parent-coverage claim."; }
    }
    #refinement dependency auditDerivation12 from BlueDogRequirements::submergedWeedPassage to BlueDogRequirements::gorgeEnvironment {
        metadata workStatus : ModelingMetadata::StatusInfo { status = ModelingMetadata::StatusKind::open; }
        metadata rationale : ModelingMetadata::Rationale { text = "N-053 specifies a detailed acceptance condition for N-010 within their stated applicability. Selected limits, mechanisms and campaign conditions remain independent allocations; refinement makes no satisfaction implication or automatic parent-coverage claim."; }
    }
    #refinement dependency auditDerivation13 from BlueDogRequirements::weedSnagShedding to BlueDogRequirements::gorgeEnvironment {
        metadata workStatus : ModelingMetadata::StatusInfo { status = ModelingMetadata::StatusKind::open; }
        metadata rationale : ModelingMetadata::Rationale { text = "N-054 specifies a detailed acceptance condition for N-010 within their stated applicability. Selected limits, mechanisms and campaign conditions remain independent allocations; refinement makes no satisfaction implication or automatic parent-coverage claim."; }
    }

    // Independently verifiable acceptance leaves.
    requirement def <'E-101'> EnergyEstimateCadence {
        metadata workStatus : ModelingMetadata::StatusInfo { status = ModelingMetadata::StatusKind::open; }
        doc /* The vessel shall refresh usable battery-energy estimates at least once per second. */
        comment conditions /*
         *  Apply the E-001 qualification conditions for this criterion. Explicit mode coverage and independent shared obligations stated in E-101 continue to govern. */
    }
    requirement energyEstimateCadence : EnergyEstimateCadence;
    #refinement dependency decomposeEnergyEstimateCadence from BlueDogRequirements::energyEstimateCadence to BlueDogRequirements::energyAwareness {
        metadata workStatus : ModelingMetadata::StatusInfo { status = ModelingMetadata::StatusKind::open; }
        metadata rationale : ModelingMetadata::Rationale { text = "E-101 specifies a detailed acceptance condition for E-001 within their stated applicability. Selected limits, mechanisms and campaign conditions remain independent allocations; refinement makes no satisfaction implication or automatic parent-coverage claim."; }
    }

    requirement def <'E-102'> ReserveEstimateCadence {
        metadata workStatus : ModelingMetadata::StatusInfo { status = ModelingMetadata::StatusKind::open; }
        doc /* The vessel shall refresh protected recovery-reserve estimates at least once per second. */
        comment conditions /*
         *  Apply the E-001 qualification conditions for this criterion. Explicit mode coverage and independent shared obligations stated in E-102 continue to govern. */
    }
    requirement reserveEstimateCadence : ReserveEstimateCadence;
    #refinement dependency decomposeReserveEstimateCadence from BlueDogRequirements::reserveEstimateCadence to BlueDogRequirements::energyAwareness {
        metadata workStatus : ModelingMetadata::StatusInfo { status = ModelingMetadata::StatusKind::open; }
        metadata rationale : ModelingMetadata::Rationale { text = "E-102 specifies a detailed acceptance condition for E-001 within their stated applicability. Selected limits, mechanisms and campaign conditions remain independent allocations; refinement makes no satisfaction implication or automatic parent-coverage claim."; }
    }

    requirement def <'E-103'> EnergyEstimateAccuracy {
        metadata workStatus : ModelingMetadata::StatusInfo { status = ModelingMetadata::StatusKind::open; }
        doc /*
         *  Across the operating battery-temperature range, the absolute difference between estimated usable energy and calibrated charge/discharge integration shall not exceed 10 percent of measured usable full-charge energy. */
        comment conditions /*
         *  Apply the E-001 qualification conditions for this criterion. Explicit mode coverage and independent shared obligations stated in E-103 continue to govern. */
    }
    requirement energyEstimateAccuracy : EnergyEstimateAccuracy;
    #refinement dependency decomposeEnergyEstimateAccuracy from BlueDogRequirements::energyEstimateAccuracy to BlueDogRequirements::energyAwareness {
        metadata workStatus : ModelingMetadata::StatusInfo { status = ModelingMetadata::StatusKind::open; }
        metadata rationale : ModelingMetadata::Rationale { text = "E-103 specifies a detailed acceptance condition for E-001 within their stated applicability. Selected limits, mechanisms and campaign conditions remain independent allocations; refinement makes no satisfaction implication or automatic parent-coverage claim."; }
    }

    requirement def <'E-104'> ConservativeEnergyEstimate {
        metadata workStatus : ModelingMetadata::StatusInfo { status = ModelingMetadata::StatusKind::open; }
        doc /* The usable-energy input to admission and low-energy decisions shall equal estimated usable energy minus the EnergyEstimateAccuracy error allowance. */
        comment conditions /*
         *  Apply the E-001 qualification conditions for this criterion. Explicit mode coverage and independent shared obligations stated in E-104 continue to govern. */
    }
    requirement conservativeEnergyEstimate : ConservativeEnergyEstimate;
    #refinement dependency decomposeConservativeEnergyEstimate from BlueDogRequirements::conservativeEnergyEstimate to BlueDogRequirements::energyAwareness {
        metadata workStatus : ModelingMetadata::StatusInfo { status = ModelingMetadata::StatusKind::open; }
        metadata rationale : ModelingMetadata::Rationale { text = "E-104 specifies a detailed acceptance condition for E-001 within their stated applicability. Selected limits, mechanisms and campaign conditions remain independent allocations; refinement makes no satisfaction implication or automatic parent-coverage claim."; }
    }

    requirement def <'E-105'> GuidanceUpdateCadence {
        metadata workStatus : ModelingMetadata::StatusInfo { status = ModelingMetadata::StatusKind::open; }
        doc /*
         *  During operational qualification, mission guidance shall refresh its guidance output at intervals no greater than 1 second. */
        comment observationBoundary /*
         *  Observe refresh at the guidance output consumed by control, or at the actuator command input, respectively. Repeated values count as a refresh; changed values and achieved physical motion are not required by this cadence criterion. */
        comment conditions /*
         *  Apply the E-002 qualification conditions for this criterion. Explicit mode coverage and independent shared obligations stated in E-105 continue to govern. */
    }
    requirement guidanceUpdateCadence : GuidanceUpdateCadence;
    #refinement dependency decomposeGuidanceUpdateCadence from BlueDogRequirements::guidanceUpdateCadence to BlueDogRequirements::navigationAndControl {
        metadata workStatus : ModelingMetadata::StatusInfo { status = ModelingMetadata::StatusKind::open; }
        metadata rationale : ModelingMetadata::Rationale { text = "E-105 specifies a detailed acceptance condition for E-002 within their stated applicability. Selected limits, mechanisms and campaign conditions remain independent allocations; refinement makes no satisfaction implication or automatic parent-coverage claim."; }
    }

    requirement def <'E-106'> SailCommandCadence {
        metadata workStatus : ModelingMetadata::StatusInfo { status = ModelingMetadata::StatusKind::open; }
        doc /*
         *  During operational qualification, sail control shall refresh the commanded sail position at intervals no greater than 1 second. */
        comment observationBoundary /*
         *  Observe refresh at the guidance output consumed by control, or at the actuator command input, respectively. Repeated values count as a refresh; changed values and achieved physical motion are not required by this cadence criterion. */
        comment conditions /*
         *  Apply the E-002 qualification conditions for this criterion. Explicit mode coverage and independent shared obligations stated in E-106 continue to govern. */
    }
    requirement sailCommandCadence : SailCommandCadence;
    #refinement dependency decomposeSailCommandCadence from BlueDogRequirements::sailCommandCadence to BlueDogRequirements::navigationAndControl {
        metadata workStatus : ModelingMetadata::StatusInfo { status = ModelingMetadata::StatusKind::open; }
        metadata rationale : ModelingMetadata::Rationale { text = "E-106 specifies a detailed acceptance condition for E-002 within their stated applicability. Selected limits, mechanisms and campaign conditions remain independent allocations; refinement makes no satisfaction implication or automatic parent-coverage claim."; }
    }

    requirement def <'E-107'> SteeringCommandCadence {
        metadata workStatus : ModelingMetadata::StatusInfo { status = ModelingMetadata::StatusKind::open; }
        doc /*
         *  During operational qualification, steering control shall refresh the commanded steering position at intervals no greater than 1 second. */
        comment observationBoundary /*
         *  Observe refresh at the guidance output consumed by control, or at the actuator command input, respectively. Repeated values count as a refresh; changed values and achieved physical motion are not required by this cadence criterion. */
        comment conditions /*
         *  Apply the E-002 qualification conditions for this criterion. Explicit mode coverage and independent shared obligations stated in E-107 continue to govern. */
    }
    requirement steeringCommandCadence : SteeringCommandCadence;
    #refinement dependency decomposeSteeringCommandCadence from BlueDogRequirements::steeringCommandCadence to BlueDogRequirements::navigationAndControl {
        metadata workStatus : ModelingMetadata::StatusInfo { status = ModelingMetadata::StatusKind::open; }
        metadata rationale : ModelingMetadata::Rationale { text = "E-107 specifies a detailed acceptance condition for E-002 within their stated applicability. Selected limits, mechanisms and campaign conditions remain independent allocations; refinement makes no satisfaction implication or automatic parent-coverage claim."; }
    }

    requirement def <'E-108'> PositionAccuracy {
        metadata workStatus : ModelingMetadata::StatusInfo { status = ModelingMetadata::StatusKind::open; }
        doc /* At every epoch in the common E-002 acceptance set, valid position error shall be at most 10 m against an independent reference. */
        comment conditions /*
         *  Apply the E-002 qualification conditions for this criterion. Explicit mode coverage and independent shared obligations stated in E-108 continue to govern. */
    }
    requirement positionAccuracy : PositionAccuracy;
    #refinement dependency decomposePositionAccuracy from BlueDogRequirements::positionAccuracy to BlueDogRequirements::navigationAndControl {
        metadata workStatus : ModelingMetadata::StatusInfo { status = ModelingMetadata::StatusKind::open; }
        metadata rationale : ModelingMetadata::Rationale { text = "E-108 specifies a detailed acceptance condition for E-002 within their stated applicability. Selected limits, mechanisms and campaign conditions remain independent allocations; refinement makes no satisfaction implication or automatic parent-coverage claim."; }
    }

    requirement def <'E-109'> HeadingAccuracy {
        metadata workStatus : ModelingMetadata::StatusInfo { status = ModelingMetadata::StatusKind::open; }
        doc /* At every epoch in the common E-002 acceptance set, valid heading error shall be at most 10 degrees against an independent reference. */
        comment conditions /*
         *  Apply the E-002 qualification conditions for this criterion. Explicit mode coverage and independent shared obligations stated in E-109 continue to govern. */
    }
    requirement headingAccuracy : HeadingAccuracy;
    #refinement dependency decomposeHeadingAccuracy from BlueDogRequirements::headingAccuracy to BlueDogRequirements::navigationAndControl {
        metadata workStatus : ModelingMetadata::StatusInfo { status = ModelingMetadata::StatusKind::open; }
        metadata rationale : ModelingMetadata::Rationale { text = "E-109 specifies a detailed acceptance condition for E-002 within their stated applicability. Selected limits, mechanisms and campaign conditions remain independent allocations; refinement makes no satisfaction implication or automatic parent-coverage claim."; }
    }

    requirement def <'E-110'> RestartDeadline {
        metadata workStatus : ModelingMetadata::StatusInfo { status = ModelingMetadata::StatusKind::open; }
        doc /* After a watchdog reset under E-003 preconditions, the vessel shall restore mode-appropriate autonomous control within 30 seconds. */
        attribute measuredRestartTime : TimeValue;
        require constraint restartDeadline {
            measuredRestartTime >= 0 [s] and measuredRestartTime <= 30 [s]
        }
        comment conditions /*
         *  Apply the E-003 qualification conditions for this criterion. Explicit mode coverage and independent shared obligations stated in E-110 continue to govern. */
    }
    requirement restartDeadline : RestartDeadline;
    #refinement dependency decomposeRestartDeadline from BlueDogRequirements::restartDeadline to BlueDogRequirements::resetRecovery {
        metadata workStatus : ModelingMetadata::StatusInfo { status = ModelingMetadata::StatusKind::open; }
        metadata rationale : ModelingMetadata::Rationale { text = "E-110 specifies a detailed acceptance condition for E-003 within their stated applicability. Selected limits, mechanisms and campaign conditions remain independent allocations; refinement makes no satisfaction implication or automatic parent-coverage claim."; }
    }

    requirement def <'E-111'> MissionStateRestoration {
        metadata workStatus : ModelingMetadata::StatusInfo { status = ModelingMetadata::StatusKind::open; }
        doc /* Within 30 seconds after a watchdog reset under E-003 preconditions, the restored mission-mode record shall equal the last persisted mode. */
        comment conditions /* Restoring recorded mission intent does not command that operating mode. Current safety, capsize, energy, recovery and isolation restrictions govern actual operation under E-113 and N-035. */
    }
    requirement missionStateRestoration : MissionStateRestoration;
    #refinement dependency decomposeMissionStateRestoration from BlueDogRequirements::missionStateRestoration to BlueDogRequirements::resetRecovery {
        metadata workStatus : ModelingMetadata::StatusInfo { status = ModelingMetadata::StatusKind::open; }
        metadata rationale : ModelingMetadata::Rationale { text = "E-111 specifies a detailed acceptance condition for E-003 within their stated applicability. Selected limits, mechanisms and campaign conditions remain independent allocations; refinement makes no satisfaction implication or automatic parent-coverage claim."; }
    }

    requirement def <'E-112'> GateProgressRestoration {
        metadata workStatus : ModelingMetadata::StatusInfo { status = ModelingMetadata::StatusKind::open; }
        doc /* Within 30 seconds after a watchdog reset under E-003 preconditions, restored gate progress shall equal the last persisted gate progress. */
        comment conditions /*
         *  Apply the E-003 qualification conditions for this criterion. Explicit mode coverage and independent shared obligations stated in E-112 continue to govern. */
    }
    requirement gateProgressRestoration : GateProgressRestoration;
    #refinement dependency decomposeGateProgressRestoration from BlueDogRequirements::gateProgressRestoration to BlueDogRequirements::resetRecovery {
        metadata workStatus : ModelingMetadata::StatusInfo { status = ModelingMetadata::StatusKind::open; }
        metadata rationale : ModelingMetadata::Rationale { text = "E-112 specifies a detailed acceptance condition for E-003 within their stated applicability. Selected limits, mechanisms and campaign conditions remain independent allocations; refinement makes no satisfaction implication or automatic parent-coverage claim."; }
    }

    requirement def <'E-113'> ResetRestrictionPreservation {
        metadata workStatus : ModelingMetadata::StatusInfo { status = ModelingMetadata::StatusKind::open; }
        doc /* After watchdog reset, each active survival, low-energy, recovery and isolation restriction shall remain effective until its own release condition is met. */
        comment conditions /*
         *  Apply the E-003 qualification conditions for this criterion. Explicit mode coverage and independent shared obligations stated in E-113 continue to govern. */
    }
    requirement resetRestrictionPreservation : ResetRestrictionPreservation;

    #derivation connection decomposeResetRestrictionPreservation {
        metadata workStatus : ModelingMetadata::StatusInfo { status = ModelingMetadata::StatusKind::open; }
        metadata rationale : ModelingMetadata::Rationale { text = "This leaf isolates one acceptance outcome of E-003; the parent supplies shared verification conditions."; }
        end #original source ::> resetRecovery;
        end #derive target ::> resetRestrictionPreservation;
    }

    requirement def <'E-114'> LowEnergyEntry {
        metadata workStatus : ModelingMetadata::StatusInfo { status = ModelingMetadata::StatusKind::open; }
        doc /* When conservative usable energy reaches or falls below protected reserve, the vessel shall set the low-energy flag within 5 seconds. */
        comment conditions /*
         *  Apply the E-004 qualification conditions for this criterion. Explicit mode coverage and independent shared obligations stated in E-114 continue to govern. */
    }
    requirement lowEnergyEntry : LowEnergyEntry;
    #refinement dependency decomposeLowEnergyEntry from BlueDogRequirements::lowEnergyEntry to BlueDogRequirements::lowEnergyRecovery {
        metadata workStatus : ModelingMetadata::StatusInfo { status = ModelingMetadata::StatusKind::open; }
        metadata rationale : ModelingMetadata::Rationale { text = "E-114 specifies a detailed acceptance condition for E-004 within their stated applicability. Selected limits, mechanisms and campaign conditions remain independent allocations; refinement makes no satisfaction implication or automatic parent-coverage claim."; }
    }

    requirement def <'E-115'> LowEnergyPayloadInhibition {
        metadata workStatus : ModelingMetadata::StatusInfo { status = ModelingMetadata::StatusKind::open; }
        doc /* While the low-energy flag is set, the optional observation payload shall be disabled. */
        comment conditions /*
         *  Apply the E-004 qualification conditions for this criterion. Explicit mode coverage and independent shared obligations stated in E-115 continue to govern. */
    }
    requirement lowEnergyPayloadInhibition : LowEnergyPayloadInhibition;
    #refinement dependency decomposeLowEnergyPayloadInhibition from BlueDogRequirements::lowEnergyPayloadInhibition to BlueDogRequirements::lowEnergyRecovery {
        metadata workStatus : ModelingMetadata::StatusInfo { status = ModelingMetadata::StatusKind::open; }
        metadata rationale : ModelingMetadata::Rationale { text = "E-115 specifies a detailed acceptance condition for E-004 within their stated applicability. Selected limits, mechanisms and campaign conditions remain independent allocations; refinement makes no satisfaction implication or automatic parent-coverage claim."; }
    }

    requirement def <'E-116'> LowEnergyNavigationContinuity {
        metadata workStatus : ModelingMetadata::StatusInfo { status = ModelingMetadata::StatusKind::open; }
        doc /* While the low-energy flag is set, autonomous navigation shall remain active. */
        comment conditions /*
         *  Apply the E-004 qualification conditions for this criterion. Explicit mode coverage and independent shared obligations stated in E-116 continue to govern. */
    }
    requirement lowEnergyNavigationContinuity : LowEnergyNavigationContinuity;
    #refinement dependency decomposeLowEnergyNavigationContinuity from BlueDogRequirements::lowEnergyNavigationContinuity to BlueDogRequirements::lowEnergyRecovery {
        metadata workStatus : ModelingMetadata::StatusInfo { status = ModelingMetadata::StatusKind::open; }
        metadata rationale : ModelingMetadata::Rationale { text = "E-116 specifies a detailed acceptance condition for E-004 within their stated applicability. Selected limits, mechanisms and campaign conditions remain independent allocations; refinement makes no satisfaction implication or automatic parent-coverage claim."; }
    }

    requirement def <'E-117'> LowEnergyCollisionContinuity {
        metadata workStatus : ModelingMetadata::StatusInfo { status = ModelingMetadata::StatusKind::open; }
        doc /* While the low-energy flag is set, collision-response behavior shall remain active. */
        comment conditions /*
         *  Apply the E-004 qualification conditions for this criterion. Explicit mode coverage and independent shared obligations stated in E-117 continue to govern. */
    }
    requirement lowEnergyCollisionContinuity : LowEnergyCollisionContinuity;
    #refinement dependency decomposeLowEnergyCollisionContinuity from BlueDogRequirements::lowEnergyCollisionContinuity to BlueDogRequirements::lowEnergyRecovery {
        metadata workStatus : ModelingMetadata::StatusInfo { status = ModelingMetadata::StatusKind::open; }
        metadata rationale : ModelingMetadata::Rationale { text = "E-117 specifies a detailed acceptance condition for E-004 within their stated applicability. Selected limits, mechanisms and campaign conditions remain independent allocations; refinement makes no satisfaction implication or automatic parent-coverage claim."; }
    }

    requirement def <'E-118'> LowEnergyExit {
        metadata workStatus : ModelingMetadata::StatusInfo { status = ModelingMetadata::StatusKind::open; }
        doc /* After conservative usable energy exceeds 1.2 times protected reserve for 10 continuous minutes, the vessel shall clear the low-energy flag independently of survival/recovery flags. */
        comment conditions /*
         *  Apply the E-004 qualification conditions for this criterion. Explicit mode coverage and independent shared obligations stated in E-118 continue to govern. */
    }
    requirement lowEnergyExit : LowEnergyExit;
    #refinement dependency decomposeLowEnergyExit from BlueDogRequirements::lowEnergyExit to BlueDogRequirements::lowEnergyRecovery {
        metadata workStatus : ModelingMetadata::StatusInfo { status = ModelingMetadata::StatusKind::open; }
        metadata rationale : ModelingMetadata::Rationale { text = "E-118 specifies a detailed acceptance condition for E-004 within their stated applicability. Selected limits, mechanisms and campaign conditions remain independent allocations; refinement makes no satisfaction implication or automatic parent-coverage claim."; }
    }

    requirement def <'E-119'> PayloadRestartPermission {
        metadata workStatus : ModelingMetadata::StatusInfo { status = ModelingMetadata::StatusKind::open; }
        doc /* Payload operation shall remain inhibited whenever a low-energy, survival or recovery restriction is active. */
        comment conditions /*
         *  Apply the E-004 qualification conditions for this criterion. Explicit mode coverage and independent shared obligations stated in E-119 continue to govern. */
    }
    requirement payloadRestartPermission : PayloadRestartPermission;
    #refinement dependency decomposePayloadRestartPermission from BlueDogRequirements::payloadRestartPermission to BlueDogRequirements::lowEnergyRecovery {
        metadata workStatus : ModelingMetadata::StatusInfo { status = ModelingMetadata::StatusKind::open; }
        metadata rationale : ModelingMetadata::Rationale { text = "E-119 specifies a detailed acceptance condition for E-004 within their stated applicability. Selected limits, mechanisms and campaign conditions remain independent allocations; refinement makes no satisfaction implication or automatic parent-coverage claim."; }
    }

    requirement def <'E-120'> TelemetryDeliveryCadence {
        metadata workStatus : ModelingMetadata::StatusInfo { status = ModelingMetadata::StatusKind::open; }
        doc /* With a functioning link, current position, operating mode and health telemetry delivery intervals shall not exceed 30 seconds. */
        comment conditions /*
         *  Apply the E-005 qualification conditions for this criterion. Explicit mode coverage and independent shared obligations stated in E-120 continue to govern. */
    }
    requirement telemetryDeliveryCadence : TelemetryDeliveryCadence;

    #derivation connection decomposeTelemetryDeliveryCadence {
        metadata workStatus : ModelingMetadata::StatusInfo { status = ModelingMetadata::StatusKind::open; }
        metadata rationale : ModelingMetadata::Rationale { text = "This leaf isolates one acceptance outcome of E-005; the parent supplies shared verification conditions."; }
        end #original source ::> communications;
        end #derive target ::> telemetryDeliveryCadence;
    }

    requirement def <'E-121'> OutageAutonomy {
        metadata workStatus : ModelingMetadata::StatusInfo { status = ModelingMetadata::StatusKind::open; }
        doc /* Through a 24-hour telemetry-link outage, autonomous mission control shall continue without operator intervention. */
        comment conditions /*
         *  Apply the E-005 qualification conditions for this criterion. Explicit mode coverage and independent shared obligations stated in E-121 continue to govern. */
    }
    requirement outageAutonomy : OutageAutonomy;
    #refinement dependency decomposeOutageAutonomy from BlueDogRequirements::outageAutonomy to BlueDogRequirements::communications {
        metadata workStatus : ModelingMetadata::StatusInfo { status = ModelingMetadata::StatusKind::open; }
        metadata rationale : ModelingMetadata::Rationale { text = "E-121 specifies a detailed acceptance condition for E-005 within their stated applicability. Selected limits, mechanisms and campaign conditions remain independent allocations; refinement makes no satisfaction implication or automatic parent-coverage claim."; }
    }

    requirement def <'E-122'> ReconnectCurrentRecord {
        metadata workStatus : ModelingMetadata::StatusInfo { status = ModelingMetadata::StatusKind::open; }
        doc /* After link restoration, a current telemetry record shall arrive within the active TelemetryDeliveryCadence interval. */
        comment conditions /*
         *  Apply the E-005 qualification conditions for this criterion. Explicit mode coverage and independent shared obligations stated in E-122 continue to govern. */
    }
    requirement reconnectCurrentRecord : ReconnectCurrentRecord;
    #refinement dependency decomposeReconnectCurrentRecord from BlueDogRequirements::reconnectCurrentRecord to BlueDogRequirements::communications {
        metadata workStatus : ModelingMetadata::StatusInfo { status = ModelingMetadata::StatusKind::open; }
        metadata rationale : ModelingMetadata::Rationale { text = "E-122 specifies a detailed acceptance condition for E-005 within their stated applicability. Selected limits, mechanisms and campaign conditions remain independent allocations; refinement makes no satisfaction implication or automatic parent-coverage claim."; }
    }

    requirement def <'E-123'> BacklogOrdering {
        metadata workStatus : ModelingMetadata::StatusInfo { status = ModelingMetadata::StatusKind::open; }
        doc /* After reconnection, retained backlog records shall be transmitted in ascending acquisition sequence order. */
        comment conditions /*
         *  Apply the E-005 qualification conditions for this criterion. Explicit mode coverage and independent shared obligations stated in E-123 continue to govern. */
    }
    requirement backlogOrdering : BacklogOrdering;
    #refinement dependency decomposeBacklogOrdering from BlueDogRequirements::backlogOrdering to BlueDogRequirements::communications {
        metadata workStatus : ModelingMetadata::StatusInfo { status = ModelingMetadata::StatusKind::open; }
        metadata rationale : ModelingMetadata::Rationale { text = "E-123 specifies a detailed acceptance condition for E-005 within their stated applicability. Selected limits, mechanisms and campaign conditions remain independent allocations; refinement makes no satisfaction implication or automatic parent-coverage claim."; }
    }

    requirement def <'E-124'> BacklogCurrentPriority {
        metadata workStatus : ModelingMetadata::StatusInfo { status = ModelingMetadata::StatusKind::open; }
        doc /* During backlog transfer, current telemetry shall continue to meet TelemetryDeliveryCadence. */
        comment conditions /*
         *  Apply the E-005 qualification conditions for this criterion. Explicit mode coverage and independent shared obligations stated in E-124 continue to govern. */
    }
    requirement backlogCurrentPriority : BacklogCurrentPriority;

    #derivation connection decomposeBacklogCurrentPriority {
        metadata workStatus : ModelingMetadata::StatusInfo { status = ModelingMetadata::StatusKind::open; }
        metadata rationale : ModelingMetadata::Rationale { text = "This leaf isolates one acceptance outcome of E-005; the parent supplies shared verification conditions."; }
        end #original source ::> communications;
        end #derive target ::> backlogCurrentPriority;
    }

    requirement def <'E-125'> IngressDetection {
        metadata workStatus : ModelingMetadata::StatusInfo { status = ModelingMetadata::StatusKind::open; }
        doc /* In the E-006 injection test, ingress detection shall occur within 60 seconds of injection starting. */
        comment conditions /*
         *  Apply the E-006 qualification conditions for this criterion. Explicit mode coverage and independent shared obligations stated in E-125 continue to govern. */
    }
    requirement ingressDetection : IngressDetection;
    #refinement dependency decomposeIngressDetection from BlueDogRequirements::ingressDetection to BlueDogRequirements::ingressResponse {
        metadata workStatus : ModelingMetadata::StatusInfo { status = ModelingMetadata::StatusKind::open; }
        metadata rationale : ModelingMetadata::Rationale { text = "E-125 specifies a detailed acceptance condition for E-006 within their stated applicability. Selected limits, mechanisms and campaign conditions remain independent allocations; refinement makes no satisfaction implication or automatic parent-coverage claim."; }
    }

    requirement def <'E-126'> IngressRecoveryRequest {
        metadata workStatus : ModelingMetadata::StatusInfo { status = ModelingMetadata::StatusKind::open; }
        doc /* In the E-006 test, ingress detection shall set the recovery-request state. */
        comment conditions /*
         *  Apply the E-006 qualification conditions for this criterion. Explicit mode coverage and independent shared obligations stated in E-126 continue to govern. */
    }
    requirement ingressRecoveryRequest : IngressRecoveryRequest;
    #refinement dependency decomposeIngressRecoveryRequest from BlueDogRequirements::ingressRecoveryRequest to BlueDogRequirements::ingressResponse {
        metadata workStatus : ModelingMetadata::StatusInfo { status = ModelingMetadata::StatusKind::open; }
        metadata rationale : ModelingMetadata::Rationale { text = "E-126 specifies a detailed acceptance condition for E-006 within their stated applicability. Selected limits, mechanisms and campaign conditions remain independent allocations; refinement makes no satisfaction implication or automatic parent-coverage claim."; }
    }

    requirement def <'E-127'> IngressFlotation {
        metadata workStatus : ModelingMetadata::StatusInfo { status = ModelingMetadata::StatusKind::open; }
        doc /* In the E-006 test, the vessel shall remain afloat for the full 30 minutes. */
        comment conditions /*
         *  Apply the E-006 qualification conditions for this criterion. Explicit mode coverage and independent shared obligations stated in E-127 continue to govern. */
    }
    requirement ingressFlotation : IngressFlotation;
    #refinement dependency decomposeIngressFlotation from BlueDogRequirements::ingressFlotation to BlueDogRequirements::ingressResponse {
        metadata workStatus : ModelingMetadata::StatusInfo { status = ModelingMetadata::StatusKind::open; }
        metadata rationale : ModelingMetadata::Rationale { text = "E-127 specifies a detailed acceptance condition for E-006 within their stated applicability. Selected limits, mechanisms and campaign conditions remain independent allocations; refinement makes no satisfaction implication or automatic parent-coverage claim."; }
    }

    requirement def <'E-128'> IngressElectronicsProtection {
        metadata workStatus : ModelingMetadata::StatusInfo { status = ModelingMetadata::StatusKind::open; }
        doc /* After the E-006 test, enclosed-electronics water-sensitive indicators shall show no liquid ingress. */
        comment conditions /*
         *  Apply the E-006 qualification conditions for this criterion. Explicit mode coverage and independent shared obligations stated in E-128 continue to govern. */
    }
    requirement ingressElectronicsProtection : IngressElectronicsProtection;
    #refinement dependency decomposeIngressElectronicsProtection from BlueDogRequirements::ingressElectronicsProtection to BlueDogRequirements::ingressResponse {
        metadata workStatus : ModelingMetadata::StatusInfo { status = ModelingMetadata::StatusKind::open; }
        metadata rationale : ModelingMetadata::Rationale { text = "E-128 specifies a detailed acceptance condition for E-006 within their stated applicability. Selected limits, mechanisms and campaign conditions remain independent allocations; refinement makes no satisfaction implication or automatic parent-coverage claim."; }
    }

    requirement def <'E-129'> IngressPositionContinuity {
        metadata workStatus : ModelingMetadata::StatusInfo { status = ModelingMetadata::StatusKind::open; }
        doc /* Throughout the E-006 test with a functioning link, position reporting shall meet the active TelemetryDeliveryCadence. */
        comment conditions /*
         *  Apply the E-006 qualification conditions for this criterion. Explicit mode coverage and independent shared obligations stated in E-129 continue to govern. */
    }
    requirement ingressPositionContinuity : IngressPositionContinuity;
    #refinement dependency decomposeIngressPositionContinuity from BlueDogRequirements::ingressPositionContinuity to BlueDogRequirements::ingressResponse {
        metadata workStatus : ModelingMetadata::StatusInfo { status = ModelingMetadata::StatusKind::open; }
        metadata rationale : ModelingMetadata::Rationale { text = "E-129 specifies a detailed acceptance condition for E-006 within their stated applicability. Selected limits, mechanisms and campaign conditions remain independent allocations; refinement makes no satisfaction implication or automatic parent-coverage claim."; }
    }

    requirement def <'E-130'> PeriodicLogCadence {
        metadata workStatus : ModelingMetadata::StatusInfo { status = ModelingMetadata::StatusKind::open; }
        doc /* Periodic mission records shall be acquired at least once per second normally and once per minute in low-energy or survival operation. */
        comment conditions /*
         *  Apply the E-007 qualification conditions for this criterion. Explicit mode coverage and independent shared obligations stated in E-130 continue to govern. */
    }
    requirement periodicLogCadence : PeriodicLogCadence;
    #refinement dependency decomposePeriodicLogCadence from BlueDogRequirements::periodicLogCadence to BlueDogRequirements::missionEvidence {
        metadata workStatus : ModelingMetadata::StatusInfo { status = ModelingMetadata::StatusKind::open; }
        metadata rationale : ModelingMetadata::Rationale { text = "E-130 specifies a detailed acceptance condition for E-007 within their stated applicability. Selected limits, mechanisms and campaign conditions remain independent allocations; refinement makes no satisfaction implication or automatic parent-coverage claim."; }
    }

    requirement def <'E-131'> LogRetention {
        metadata workStatus : ModelingMetadata::StatusInfo { status = ModelingMetadata::StatusKind::open; }
        doc /* Acquired mission records shall remain retrievable onboard for at least 30 days. */
        comment conditions /*
         *  Apply the E-007 qualification conditions for this criterion. Explicit mode coverage and independent shared obligations stated in E-131 continue to govern. */
    }
    requirement logRetention : LogRetention;
    #refinement dependency decomposeLogRetention from BlueDogRequirements::logRetention to BlueDogRequirements::missionEvidence {
        metadata workStatus : ModelingMetadata::StatusInfo { status = ModelingMetadata::StatusKind::open; }
        metadata rationale : ModelingMetadata::Rationale { text = "E-131 specifies a detailed acceptance condition for E-007 within their stated applicability. Selected limits, mechanisms and campaign conditions remain independent allocations; refinement makes no satisfaction implication or automatic parent-coverage claim."; }
    }

    requirement def <'E-132'> CriticalEventRecording {
        metadata workStatus : ModelingMetadata::StatusInfo { status = ModelingMetadata::StatusKind::open; }
        doc /* Every external-command disposition, reset, motor-enable transition, ingress detection, recovery request, navigation-degraded transition, low-energy flag transition and qualification change shall have an event record regardless of periodic cadence. */
        comment conditions /*
         *  Apply the E-007 qualification conditions for this criterion. Explicit mode coverage and independent shared obligations stated in E-132 continue to govern. */
    }
    requirement criticalEventRecording : CriticalEventRecording;
    #refinement dependency decomposeCriticalEventRecording from BlueDogRequirements::criticalEventRecording to BlueDogRequirements::missionEvidence {
        metadata workStatus : ModelingMetadata::StatusInfo { status = ModelingMetadata::StatusKind::open; }
        metadata rationale : ModelingMetadata::Rationale { text = "E-132 specifies a detailed acceptance condition for E-007 within their stated applicability. Selected limits, mechanisms and campaign conditions remain independent allocations; refinement makes no satisfaction implication or automatic parent-coverage claim."; }
    }

    requirement def <'E-133'> LogTimestampAccuracy {
        metadata workStatus : ModelingMetadata::StatusInfo { status = ModelingMetadata::StatusKind::open; }
        doc /* With valid GNSS time, mission-record timestamps shall differ from reference UTC by at most 1 second. */
        comment conditions /*
         *  Apply the E-007 qualification conditions for this criterion. Explicit mode coverage and independent shared obligations stated in E-133 continue to govern. */
    }
    requirement logTimestampAccuracy : LogTimestampAccuracy;
    #refinement dependency decomposeLogTimestampAccuracy from BlueDogRequirements::logTimestampAccuracy to BlueDogRequirements::missionEvidence {
        metadata workStatus : ModelingMetadata::StatusInfo { status = ModelingMetadata::StatusKind::open; }
        metadata rationale : ModelingMetadata::Rationale { text = "E-133 specifies a detailed acceptance condition for E-007 within their stated applicability. Selected limits, mechanisms and campaign conditions remain independent allocations; refinement makes no satisfaction implication or automatic parent-coverage claim."; }
    }

    requirement def <'E-134'> InvalidTimestampMarking {
        metadata workStatus : ModelingMetadata::StatusInfo { status = ModelingMetadata::StatusKind::open; }
        doc /* Each record acquired without valid time shall carry an invalid-time indication. */
        comment conditions /*
         *  Apply the E-007 qualification conditions for this criterion. Explicit mode coverage and independent shared obligations stated in E-134 continue to govern. */
    }
    requirement invalidTimestampMarking : InvalidTimestampMarking;
    #refinement dependency decomposeInvalidTimestampMarking from BlueDogRequirements::invalidTimestampMarking to BlueDogRequirements::missionEvidence {
        metadata workStatus : ModelingMetadata::StatusInfo { status = ModelingMetadata::StatusKind::open; }
        metadata rationale : ModelingMetadata::Rationale { text = "E-134 specifies a detailed acceptance condition for E-007 within their stated applicability. Selected limits, mechanisms and campaign conditions remain independent allocations; refinement makes no satisfaction implication or automatic parent-coverage claim."; }
    }

    requirement def <'E-135'> LogGapIndication {
        metadata workStatus : ModelingMetadata::StatusInfo { status = ModelingMetadata::StatusKind::open; }
        doc /* Each detected missing sequence of scheduled records shall have a gap indication in retrieved data. */
        comment conditions /*
         *  Apply the E-007 qualification conditions for this criterion. Explicit mode coverage and independent shared obligations stated in E-135 continue to govern. */
    }
    requirement logGapIndication : LogGapIndication;
    #refinement dependency decomposeLogGapIndication from BlueDogRequirements::logGapIndication to BlueDogRequirements::missionEvidence {
        metadata workStatus : ModelingMetadata::StatusInfo { status = ModelingMetadata::StatusKind::open; }
        metadata rationale : ModelingMetadata::Rationale { text = "E-135 specifies a detailed acceptance condition for E-007 within their stated applicability. Selected limits, mechanisms and campaign conditions remain independent allocations; refinement makes no satisfaction implication or automatic parent-coverage claim."; }
    }

    requirement def <'E-136'> LogInterruptionDurability {
        metadata workStatus : ModelingMetadata::StatusInfo { status = ModelingMetadata::StatusKind::open; }
        doc /* After watchdog reset or abrupt power removal, every record older than 5 seconds before interruption shall remain readable. */
        comment conditions /*
         *  Apply the E-007 qualification conditions for this criterion. Explicit mode coverage and independent shared obligations stated in E-136 continue to govern. */
    }
    requirement logInterruptionDurability : LogInterruptionDurability;
    #refinement dependency decomposeLogInterruptionDurability from BlueDogRequirements::logInterruptionDurability to BlueDogRequirements::missionEvidence {
        metadata workStatus : ModelingMetadata::StatusInfo { status = ModelingMetadata::StatusKind::open; }
        metadata rationale : ModelingMetadata::Rationale { text = "E-136 specifies a detailed acceptance condition for E-007 within their stated applicability. Selected limits, mechanisms and campaign conditions remain independent allocations; refinement makes no satisfaction implication or automatic parent-coverage claim."; }
    }

    requirement def <'E-137'> ReconnectLogPreservation {
        metadata workStatus : ModelingMetadata::StatusInfo { status = ModelingMetadata::StatusKind::open; }
        doc /* Communication reconnection shall not delete retained mission records. */
        comment conditions /*
         *  Apply the E-007 qualification conditions for this criterion. Explicit mode coverage and independent shared obligations stated in E-137 continue to govern. */
    }
    requirement reconnectLogPreservation : ReconnectLogPreservation;
    #refinement dependency decomposeReconnectLogPreservation from BlueDogRequirements::reconnectLogPreservation to BlueDogRequirements::missionEvidence {
        metadata workStatus : ModelingMetadata::StatusInfo { status = ModelingMetadata::StatusKind::open; }
        metadata rationale : ModelingMetadata::Rationale { text = "E-137 specifies a detailed acceptance condition for E-007 within their stated applicability. Selected limits, mechanisms and campaign conditions remain independent allocations; refinement makes no satisfaction implication or automatic parent-coverage claim."; }
    }

    requirement def <'E-138'> QualificationPersistence {
        metadata workStatus : ModelingMetadata::StatusInfo { status = ModelingMetadata::StatusKind::open; }
        doc /* Each disqualifying transition shall be durably stored before its associated commanded intervention or motor enable. */
        comment conditions /*
         *  Apply the E-007 qualification conditions for this criterion. Explicit mode coverage and independent shared obligations stated in E-138 continue to govern. */
    }
    requirement qualificationPersistence : QualificationPersistence;
    #refinement dependency decomposeQualificationPersistence from BlueDogRequirements::qualificationPersistence to BlueDogRequirements::missionEvidence {
        metadata workStatus : ModelingMetadata::StatusInfo { status = ModelingMetadata::StatusKind::open; }
        metadata rationale : ModelingMetadata::Rationale { text = "E-138 specifies a detailed acceptance condition for E-007 within their stated applicability. Selected limits, mechanisms and campaign conditions remain independent allocations; refinement makes no satisfaction implication or automatic parent-coverage claim."; }
    }

    requirement def <'E-139'> UnknownQualificationFallback {
        metadata workStatus : ModelingMetadata::StatusInfo { status = ModelingMetadata::StatusKind::open; }
        doc /* On restart with absent or inconsistent persisted qualification state, the vessel shall adopt nonqualifying status. */
        comment conditions /*
         *  Apply the E-007 qualification conditions for this criterion. Explicit mode coverage and independent shared obligations stated in E-139 continue to govern. */
    }
    requirement unknownQualificationFallback : UnknownQualificationFallback;
    #refinement dependency decomposeUnknownQualificationFallback from BlueDogRequirements::unknownQualificationFallback to BlueDogRequirements::missionEvidence {
        metadata workStatus : ModelingMetadata::StatusInfo { status = ModelingMetadata::StatusKind::open; }
        metadata rationale : ModelingMetadata::Rationale { text = "E-139 specifies a detailed acceptance condition for E-007 within their stated applicability. Selected limits, mechanisms and campaign conditions remain independent allocations; refinement makes no satisfaction implication or automatic parent-coverage claim."; }
    }

    requirement def <'E-140'> NavigationValidEpochs {
        metadata workStatus : ModelingMetadata::StatusInfo { status = ModelingMetadata::StatusKind::open; }
        doc /* In each E-008 campaign, at least 1710 of 1800 scheduled epochs shall contain valid position and heading observations. */
        attribute validEpochs : Integer;
        require constraint availabilityFraction {
            validEpochs >= 1710 and validEpochs <= 1800
        }
        comment conditions /*
         *  Apply the E-008 qualification conditions for this criterion. Explicit mode coverage and independent shared obligations stated in E-140 continue to govern. */
    }
    requirement navigationValidEpochs : NavigationValidEpochs;
    #refinement dependency decomposeNavigationValidEpochs from BlueDogRequirements::navigationValidEpochs to BlueDogRequirements::navigationAvailability {
        metadata workStatus : ModelingMetadata::StatusInfo { status = ModelingMetadata::StatusKind::open; }
        metadata rationale : ModelingMetadata::Rationale { text = "E-140 specifies a detailed acceptance condition for E-008 within their stated applicability. Selected limits, mechanisms and campaign conditions remain independent allocations; refinement makes no satisfaction implication or automatic parent-coverage claim."; }
    }

    requirement def <'E-141'> StaleNavigationInvalidation {
        metadata workStatus : ModelingMetadata::StatusInfo { status = ModelingMetadata::StatusKind::open; }
        doc /* Navigation observations older than 5 seconds shall be marked invalid. */
        comment conditions /*
         *  Apply the E-008 qualification conditions for this criterion. Explicit mode coverage and independent shared obligations stated in E-141 continue to govern. */
    }
    requirement staleNavigationInvalidation : StaleNavigationInvalidation;
    #refinement dependency decomposeStaleNavigationInvalidation from BlueDogRequirements::staleNavigationInvalidation to BlueDogRequirements::navigationAvailability {
        metadata workStatus : ModelingMetadata::StatusInfo { status = ModelingMetadata::StatusKind::open; }
        metadata rationale : ModelingMetadata::Rationale { text = "E-141 specifies a detailed acceptance condition for E-008 within their stated applicability. Selected limits, mechanisms and campaign conditions remain independent allocations; refinement makes no satisfaction implication or automatic parent-coverage claim."; }
    }

    requirement def <'E-142'> NavigationDegradedTransition {
        metadata workStatus : ModelingMetadata::StatusInfo { status = ModelingMetadata::StatusKind::open; }
        doc /* When position or heading becomes invalid due to age, the vessel shall enter navigation-degraded state within 1 second. */
        comment conditions /*
         *  Apply the E-008 qualification conditions for this criterion. Explicit mode coverage and independent shared obligations stated in E-142 continue to govern. */
    }
    requirement navigationDegradedTransition : NavigationDegradedTransition;
    #refinement dependency decomposeNavigationDegradedTransition from BlueDogRequirements::navigationDegradedTransition to BlueDogRequirements::navigationAvailability {
        metadata workStatus : ModelingMetadata::StatusInfo { status = ModelingMetadata::StatusKind::open; }
        metadata rationale : ModelingMetadata::Rationale { text = "E-142 specifies a detailed acceptance condition for E-008 within their stated applicability. Selected limits, mechanisms and campaign conditions remain independent allocations; refinement makes no satisfaction implication or automatic parent-coverage claim."; }
    }

    requirement def <'E-143'> StaleNavigationUseInhibition {
        metadata workStatus : ModelingMetadata::StatusInfo { status = ModelingMetadata::StatusKind::open; }
        doc /* The controller shall not use observations marked invalid as current navigation inputs. */
        comment conditions /*
         *  Apply the E-008 qualification conditions for this criterion. Explicit mode coverage and independent shared obligations stated in E-143 continue to govern. */
    }
    requirement staleNavigationUseInhibition : StaleNavigationUseInhibition;
    #refinement dependency decomposeStaleNavigationUseInhibition from BlueDogRequirements::staleNavigationUseInhibition to BlueDogRequirements::navigationAvailability {
        metadata workStatus : ModelingMetadata::StatusInfo { status = ModelingMetadata::StatusKind::open; }
        metadata rationale : ModelingMetadata::Rationale { text = "E-143 specifies a detailed acceptance condition for E-008 within their stated applicability. Selected limits, mechanisms and campaign conditions remain independent allocations; refinement makes no satisfaction implication or automatic parent-coverage claim."; }
    }

    requirement def <'P-101'> SoloTransport {
        metadata workStatus : ModelingMetadata::StatusInfo { status = ModelingMetadata::StatusKind::open; }
        doc /*
         *  The vessel and its mission equipment shall be transportable for 100 m by one adult without assistance under the P-001 handling conditions. */
        comment conditions /*
         *  Apply the P-001 qualification conditions for this criterion. Explicit mode coverage and independent shared obligations stated in P-101 continue to govern. */
    }
    requirement soloTransport : SoloTransport;
    #refinement dependency decomposeSoloTransport from BlueDogRequirements::soloTransport to BlueDogRequirements::transportability {
        metadata workStatus : ModelingMetadata::StatusInfo { status = ModelingMetadata::StatusKind::open; }
        metadata rationale : ModelingMetadata::Rationale { text = "P-101 specifies a detailed acceptance condition for P-001 within their stated applicability. Selected limits, mechanisms and campaign conditions remain independent allocations; refinement makes no satisfaction implication or automatic parent-coverage claim."; }
    }

    requirement def <'P-102'> LiftMass {
        metadata workStatus : ModelingMetadata::StatusInfo { status = ModelingMetadata::StatusKind::open; }
        doc /* Each separately lifted assembly shall have a mass no greater than 15 kg. */
        comment conditions /*
         *  Apply the P-001 qualification conditions for this criterion. Explicit mode coverage and independent shared obligations stated in P-102 continue to govern. */
    }
    requirement liftMass : LiftMass;
    #refinement dependency decomposeLiftMass from BlueDogRequirements::liftMass to BlueDogRequirements::transportability {
        metadata workStatus : ModelingMetadata::StatusInfo { status = ModelingMetadata::StatusKind::open; }
        metadata rationale : ModelingMetadata::Rationale { text = "P-102 specifies a detailed acceptance condition for P-001 within their stated applicability. Selected limits, mechanisms and campaign conditions remain independent allocations; refinement makes no satisfaction implication or automatic parent-coverage claim."; }
    }

    requirement def <'P-103'> SetupDuration {
        metadata workStatus : ModelingMetadata::StatusInfo { status = ModelingMetadata::StatusKind::open; }
        doc /*
         *  The vessel shall be capable of assembly from its transport configuration by one adult within 30 minutes under the P-001 handling conditions. */
        comment conditions /*
         *  Apply the P-001 qualification conditions for this criterion. Explicit mode coverage and independent shared obligations stated in P-103 continue to govern. */
    }
    requirement setupDuration : SetupDuration;
    #refinement dependency decomposeSetupDuration from BlueDogRequirements::setupDuration to BlueDogRequirements::transportability {
        metadata workStatus : ModelingMetadata::StatusInfo { status = ModelingMetadata::StatusKind::open; }
        metadata rationale : ModelingMetadata::Rationale { text = "P-103 specifies a detailed acceptance condition for P-001 within their stated applicability. Selected limits, mechanisms and campaign conditions remain independent allocations; refinement makes no satisfaction implication or automatic parent-coverage claim."; }
    }

    requirement def <'P-104'> PackDuration {
        metadata workStatus : ModelingMetadata::StatusInfo { status = ModelingMetadata::StatusKind::open; }
        doc /*
         *  The vessel shall be capable of packing into its transport configuration by one adult within 30 minutes under the P-001 handling conditions. */
        comment conditions /*
         *  Apply the P-001 qualification conditions for this criterion. Explicit mode coverage and independent shared obligations stated in P-104 continue to govern. */
    }
    requirement packDuration : PackDuration;
    #refinement dependency decomposePackDuration from BlueDogRequirements::packDuration to BlueDogRequirements::transportability {
        metadata workStatus : ModelingMetadata::StatusInfo { status = ModelingMetadata::StatusKind::open; }
        metadata rationale : ModelingMetadata::Rationale { text = "P-104 specifies a detailed acceptance condition for P-001 within their stated applicability. Selected limits, mechanisms and campaign conditions remain independent allocations; refinement makes no satisfaction implication or automatic parent-coverage claim."; }
    }

    requirement def <'P-105'> SoloLaunch {
        metadata workStatus : ModelingMetadata::StatusInfo { status = ModelingMetadata::StatusKind::open; }
        doc /*
         *  The assembled vessel shall be launchable by one adult without assistance under the P-001 handling conditions. */
        comment conditions /*
         *  Apply the P-001 qualification conditions for this criterion. Explicit mode coverage and independent shared obligations stated in P-105 continue to govern. */
    }
    requirement soloLaunch : SoloLaunch;

    #derivation connection decomposeSoloLaunch {
        metadata workStatus : ModelingMetadata::StatusInfo { status = ModelingMetadata::StatusKind::open; }
        metadata rationale : ModelingMetadata::Rationale { text = "This leaf isolates one acceptance outcome of P-001; the parent supplies shared verification conditions."; }
        end #original source ::> transportability;
        end #derive target ::> soloLaunch;
    }

    requirement def <'P-106'> SoloRetrieval {
        metadata workStatus : ModelingMetadata::StatusInfo { status = ModelingMetadata::StatusKind::open; }
        doc /*
         *  The vessel shall be retrievable from the water by one adult without assistance under the P-001 handling conditions. */
        comment conditions /*
         *  Apply the P-001 qualification conditions for this criterion. Explicit mode coverage and independent shared obligations stated in P-106 continue to govern. */
    }
    requirement soloRetrieval : SoloRetrieval;

    #derivation connection decomposeSoloRetrieval {
        metadata workStatus : ModelingMetadata::StatusInfo { status = ModelingMetadata::StatusKind::open; }
        metadata rationale : ModelingMetadata::Rationale { text = "This leaf isolates one acceptance outcome of P-001; the parent supplies shared verification conditions."; }
        end #original source ::> transportability;
        end #derive target ::> soloRetrieval;
    }

    requirement def <'P-107'> ReplacementDuration {
        metadata workStatus : ModelingMetadata::StatusInfo { status = ModelingMetadata::StatusKind::open; }
        doc /* Each P-003 replacement shall take no more than 30 minutes. */
        comment conditions /*
         *  Apply the P-003 qualification conditions for this criterion. Explicit mode coverage and independent shared obligations stated in P-107 continue to govern. */
    }
    requirement replacementDuration : ReplacementDuration;
    #refinement dependency decomposeReplacementDuration from BlueDogRequirements::replacementDuration to BlueDogRequirements::serviceability {
        metadata workStatus : ModelingMetadata::StatusInfo { status = ModelingMetadata::StatusKind::open; }
        metadata rationale : ModelingMetadata::Rationale { text = "P-107 specifies a detailed acceptance condition for P-003 within their stated applicability. Selected limits, mechanisms and campaign conditions remain independent allocations; refinement makes no satisfaction implication or automatic parent-coverage claim."; }
    }

    requirement def <'P-108'> NondestructiveService {
        metadata workStatus : ModelingMetadata::StatusInfo { status = ModelingMetadata::StatusKind::open; }
        doc /* Each P-003 replacement shall leave bonded structural joints and adjacent parts intact. */
        comment conditions /*
         *  Apply the P-003 qualification conditions for this criterion. Explicit mode coverage and independent shared obligations stated in P-108 continue to govern. */
    }
    requirement nondestructiveService : NondestructiveService;

    #derivation connection decomposeNondestructiveService {
        metadata workStatus : ModelingMetadata::StatusInfo { status = ModelingMetadata::StatusKind::open; }
        metadata rationale : ModelingMetadata::Rationale { text = "This leaf isolates one acceptance outcome of P-003; the parent supplies shared verification conditions."; }
        end #original source ::> serviceability;
        end #derive target ::> nondestructiveService;
    }

    requirement def <'P-109'> PostServiceSealing {
        metadata workStatus : ModelingMetadata::StatusInfo { status = ModelingMetadata::StatusKind::open; }
        doc /* After each P-003 replacement, the assembly shall meet the N-043 immersion criterion. */
        comment conditions /*
         *  Apply the P-003 qualification conditions for this criterion. Explicit mode coverage and independent shared obligations stated in P-109 continue to govern. */
    }
    requirement postServiceSealing : PostServiceSealing;
    #refinement dependency decomposePostServiceSealing from BlueDogRequirements::postServiceSealing to BlueDogRequirements::serviceability {
        metadata workStatus : ModelingMetadata::StatusInfo { status = ModelingMetadata::StatusKind::open; }
        metadata rationale : ModelingMetadata::Rationale { text = "P-109 specifies a detailed acceptance condition for P-003 within their stated applicability. Selected limits, mechanisms and campaign conditions remain independent allocations; refinement makes no satisfaction implication or automatic parent-coverage claim."; }
    }

    requirement def <'P-110'> PostServiceActuation {
        metadata workStatus : ModelingMetadata::StatusInfo { status = ModelingMetadata::StatusKind::open; }
        doc /* After each P-003 replacement, affected actuators shall complete their full commanded travel. */
        comment conditions /*
         *  Apply the P-003 qualification conditions for this criterion. Explicit mode coverage and independent shared obligations stated in P-110 continue to govern. */
    }
    requirement postServiceActuation : PostServiceActuation;
    #refinement dependency decomposePostServiceActuation from BlueDogRequirements::postServiceActuation to BlueDogRequirements::serviceability {
        metadata workStatus : ModelingMetadata::StatusInfo { status = ModelingMetadata::StatusKind::open; }
        metadata rationale : ModelingMetadata::Rationale { text = "P-110 specifies a detailed acceptance condition for P-003 within their stated applicability. Selected limits, mechanisms and campaign conditions remain independent allocations; refinement makes no satisfaction implication or automatic parent-coverage claim."; }
    }

    requirement def <'S-101'> TrafficTracking {
        metadata workStatus : ModelingMetadata::StatusInfo { status = ModelingMetadata::StatusKind::open; }
        doc /* The vessel shall acquire and maintain encounter tracks with the reviewed class- and condition-specific timely acquisition and continuity performance required by S-001.*/
        comment conditions /* Each admitted target class remains in scope. Before reliable classification, apply the reviewed conservative envelope spanning plausible classes and occupant transitions. */
    }
    requirement trafficTracking : TrafficTracking;
    #refinement dependency decomposeTrafficTracking from BlueDogRequirements::trafficTracking to BlueDogRequirements::trafficSafety {
        metadata workStatus : ModelingMetadata::StatusInfo { status = ModelingMetadata::StatusKind::open; }
        metadata rationale : ModelingMetadata::Rationale { text = "S-101 specifies a detailed acceptance condition for S-001 within their stated applicability. Selected limits, mechanisms and campaign conditions remain independent allocations; refinement makes no satisfaction implication or automatic parent-coverage claim."; }
    }

    requirement def <'S-102'> CollisionAssessmentCadence {
        metadata workStatus : ModelingMetadata::StatusInfo { status = ModelingMetadata::StatusKind::open; }
        doc /* The vessel shall update collision-risk estimates at least once per second. */
        comment conditions /*
         *  Apply the S-001 qualification conditions for this criterion. Explicit mode coverage and independent shared obligations stated in S-102 continue to govern. */
    }
    requirement collisionAssessmentCadence : CollisionAssessmentCadence;
    #refinement dependency decomposeCollisionAssessmentCadence from BlueDogRequirements::collisionAssessmentCadence to BlueDogRequirements::trafficSafety {
        metadata workStatus : ModelingMetadata::StatusInfo { status = ModelingMetadata::StatusKind::open; }
        metadata rationale : ModelingMetadata::Rationale { text = "S-102 specifies a detailed acceptance condition for S-001 within their stated applicability. Selected limits, mechanisms and campaign conditions remain independent allocations; refinement makes no satisfaction implication or automatic parent-coverage claim."; }
    }

    requirement def <'S-103'> AvoidanceCommandDeadline {
        metadata workStatus : ModelingMetadata::StatusInfo { status = ModelingMetadata::StatusKind::open; }
        doc /* The vessel shall issue the prescribed avoiding-action command within 2 seconds of each S-001 collision-risk trigger. */
        comment conditions /*
         *  Apply the S-001 qualification conditions for this criterion. Explicit mode coverage and independent shared obligations stated in S-103 continue to govern. */
    }
    requirement avoidanceCommandDeadline : AvoidanceCommandDeadline;
    #refinement dependency decomposeAvoidanceCommandDeadline from BlueDogRequirements::avoidanceCommandDeadline to BlueDogRequirements::trafficSafety {
        metadata workStatus : ModelingMetadata::StatusInfo { status = ModelingMetadata::StatusKind::open; }
        metadata rationale : ModelingMetadata::Rationale { text = "S-103 specifies a detailed acceptance condition for S-001 within their stated applicability. Selected limits, mechanisms and campaign conditions remain independent allocations; refinement makes no satisfaction implication or automatic parent-coverage claim."; }
    }

    requirement def <'S-104'> TrafficAwarenessFault {
        metadata workStatus : ModelingMetadata::StatusInfo { status = ModelingMetadata::StatusKind::open; }
        doc /* After traffic assessment has been invalid for more than 5 seconds, the vessel shall log a traffic-awareness fault within 1 second. */
        comment conditions /*
         *  Apply the S-001 qualification conditions for this criterion. Explicit mode coverage and independent shared obligations stated in S-104 continue to govern. */
    }
    requirement trafficAwarenessFault : TrafficAwarenessFault;
    #refinement dependency decomposeTrafficAwarenessFault from BlueDogRequirements::trafficAwarenessFault to BlueDogRequirements::trafficSafety {
        metadata workStatus : ModelingMetadata::StatusInfo { status = ModelingMetadata::StatusKind::open; }
        metadata rationale : ModelingMetadata::Rationale { text = "S-104 specifies a detailed acceptance condition for S-001 within their stated applicability. Selected limits, mechanisms and campaign conditions remain independent allocations; refinement makes no satisfaction implication or automatic parent-coverage claim."; }
    }

    requirement def <'S-105'> BoundaryEvaluationCadence {
        metadata workStatus : ModelingMetadata::StatusInfo { status = ModelingMetadata::StatusKind::open; }
        doc /* The vessel shall evaluate its current position and predicted trajectory against the S-002 polygons at least once per second. */
        comment conditions /*
         *  Apply the S-002 qualification conditions for this criterion. Explicit mode coverage and independent shared obligations stated in S-105 continue to govern. */
    }
    requirement boundaryEvaluationCadence : BoundaryEvaluationCadence;
    #refinement dependency decomposeBoundaryEvaluationCadence from BlueDogRequirements::boundaryEvaluationCadence to BlueDogRequirements::operatingBoundary {
        metadata workStatus : ModelingMetadata::StatusInfo { status = ModelingMetadata::StatusKind::open; }
        metadata rationale : ModelingMetadata::Rationale { text = "S-105 specifies a detailed acceptance condition for S-002 within their stated applicability. Selected limits, mechanisms and campaign conditions remain independent allocations; refinement makes no satisfaction implication or automatic parent-coverage claim."; }
    }

    requirement def <'S-106'> BoundaryAvoidanceDeadline {
        metadata workStatus : ModelingMetadata::StatusInfo { status = ModelingMetadata::StatusKind::open; }
        doc /* The vessel shall issue an avoidance command within 2 seconds of predicting a boundary crossing. */
        comment conditions /*
         *  Apply the S-002 qualification conditions for this criterion. Explicit mode coverage and independent shared obligations stated in S-106 continue to govern. */
    }
    requirement boundaryAvoidanceDeadline : BoundaryAvoidanceDeadline;
    #refinement dependency decomposeBoundaryAvoidanceDeadline from BlueDogRequirements::boundaryAvoidanceDeadline to BlueDogRequirements::operatingBoundary {
        metadata workStatus : ModelingMetadata::StatusInfo { status = ModelingMetadata::StatusKind::open; }
        metadata rationale : ModelingMetadata::Rationale { text = "S-106 specifies a detailed acceptance condition for S-002 within their stated applicability. Selected limits, mechanisms and campaign conditions remain independent allocations; refinement makes no satisfaction implication or automatic parent-coverage claim."; }
    }

    requirement def <'S-107'> BoundaryAvoidanceRecording {
        metadata workStatus : ModelingMetadata::StatusInfo { status = ModelingMetadata::StatusKind::open; }
        doc /* Every boundary-avoidance command shall have a corresponding event record. */
        comment conditions /*
         *  Apply the S-002 qualification conditions for this criterion. Explicit mode coverage and independent shared obligations stated in S-107 continue to govern. */
    }
    requirement boundaryAvoidanceRecording : BoundaryAvoidanceRecording;
    #refinement dependency decomposeBoundaryAvoidanceRecording from BlueDogRequirements::boundaryAvoidanceRecording to BlueDogRequirements::operatingBoundary {
        metadata workStatus : ModelingMetadata::StatusInfo { status = ModelingMetadata::StatusKind::open; }
        metadata rationale : ModelingMetadata::Rationale { text = "S-107 specifies a detailed acceptance condition for S-002 within their stated applicability. Selected limits, mechanisms and campaign conditions remain independent allocations; refinement makes no satisfaction implication or automatic parent-coverage claim."; }
    }

    requirement def <'S-108'> BoundaryStartInhibition {
        metadata workStatus : ModelingMetadata::StatusInfo { status = ModelingMetadata::StatusKind::open; }
        doc /* Missing or geometrically invalid boundaries shall inhibit mission start. */
        comment conditions /*
         *  Apply the S-002 qualification conditions for this criterion. Explicit mode coverage and independent shared obligations stated in S-108 continue to govern. */
    }
    requirement boundaryStartInhibition : BoundaryStartInhibition;
    #refinement dependency decomposeBoundaryStartInhibition from BlueDogRequirements::boundaryStartInhibition to BlueDogRequirements::operatingBoundary {
        metadata workStatus : ModelingMetadata::StatusInfo { status = ModelingMetadata::StatusKind::open; }
        metadata rationale : ModelingMetadata::Rationale { text = "S-108 specifies a detailed acceptance condition for S-002 within their stated applicability. Selected limits, mechanisms and campaign conditions remain independent allocations; refinement makes no satisfaction implication or automatic parent-coverage claim."; }
    }

    requirement def <'S-109'> BoundaryDegradedEvidence {
        metadata workStatus : ModelingMetadata::StatusInfo { status = ModelingMetadata::StatusKind::open; }
        doc /* Navigation loss or absence of a feasible maneuver shall produce an explicit degraded-route verdict instead of a safe-route verdict. */
        comment conditions /*
         *  Apply the S-002 qualification conditions for this criterion. Explicit mode coverage and independent shared obligations stated in S-109 continue to govern. */
    }
    requirement boundaryDegradedEvidence : BoundaryDegradedEvidence;
    #refinement dependency decomposeBoundaryDegradedEvidence from BlueDogRequirements::boundaryDegradedEvidence to BlueDogRequirements::operatingBoundary {
        metadata workStatus : ModelingMetadata::StatusInfo { status = ModelingMetadata::StatusKind::open; }
        metadata rationale : ModelingMetadata::Rationale { text = "S-109 specifies a detailed acceptance condition for S-002 within their stated applicability. Selected limits, mechanisms and campaign conditions remain independent allocations; refinement makes no satisfaction implication or automatic parent-coverage claim."; }
    }

    requirement def <'S-110'> AbortLatchDeadline {
        metadata workStatus : ModelingMetadata::StatusInfo { status = ModelingMetadata::StatusKind::open; }
        doc /* After accepting emergency abort, the vessel shall latch the attempt as disqualified within 1 second. */
        comment conditions /*
         *  Apply the S-003 qualification conditions for this criterion. Explicit mode coverage and independent shared obligations stated in S-110 continue to govern. */
    }
    requirement abortLatchDeadline : AbortLatchDeadline;
    #refinement dependency decomposeAbortLatchDeadline from BlueDogRequirements::abortLatchDeadline to BlueDogRequirements::emergencyControl {
        metadata workStatus : ModelingMetadata::StatusInfo { status = ModelingMetadata::StatusKind::open; }
        metadata rationale : ModelingMetadata::Rationale { text = "S-110 specifies a detailed acceptance condition for S-003 within their stated applicability. Selected limits, mechanisms and campaign conditions remain independent allocations; refinement makes no satisfaction implication or automatic parent-coverage claim."; }
    }

    requirement def <'S-111'> RecoveryTelemetryCadence {
        metadata workStatus : ModelingMetadata::StatusInfo { status = ModelingMetadata::StatusKind::open; }
        doc /* During active emergency or powered recovery with a functioning link, the vessel shall deliver position telemetry at least once per 30 seconds, including low-energy operation. */
        comment conditions /*
         *  Apply the S-003 qualification conditions for this criterion. Explicit mode coverage and independent shared obligations stated in S-111 continue to govern. */
    }
    requirement recoveryTelemetryCadence : RecoveryTelemetryCadence;
    #refinement dependency decomposeRecoveryTelemetryCadence from BlueDogRequirements::recoveryTelemetryCadence to BlueDogRequirements::emergencyControl {
        metadata workStatus : ModelingMetadata::StatusInfo { status = ModelingMetadata::StatusKind::open; }
        metadata rationale : ModelingMetadata::Rationale { text = "S-111 specifies a detailed acceptance condition for S-003 within their stated applicability. Selected limits, mechanisms and campaign conditions remain independent allocations; refinement makes no satisfaction implication or automatic parent-coverage claim."; }
    }

    requirement def <'S-112'> MotorIsolationDeadline {
        metadata workStatus : ModelingMetadata::StatusInfo { status = ModelingMetadata::StatusKind::open; }
        doc /* A physically accessible local isolation control shall remove motor power within 1 second of activation. */
        comment conditions /*
         *  Apply the S-003 qualification conditions for this criterion. Explicit mode coverage and independent shared obligations stated in S-112 continue to govern. */
    }
    requirement motorIsolationDeadline : MotorIsolationDeadline;
    #refinement dependency decomposeMotorIsolationDeadline from BlueDogRequirements::motorIsolationDeadline to BlueDogRequirements::emergencyControl {
        metadata workStatus : ModelingMetadata::StatusInfo { status = ModelingMetadata::StatusKind::open; }
        metadata rationale : ModelingMetadata::Rationale { text = "S-112 specifies a detailed acceptance condition for S-003 within their stated applicability. Selected limits, mechanisms and campaign conditions remain independent allocations; refinement makes no satisfaction implication or automatic parent-coverage claim."; }
    }

    requirement def <'S-113'> IsolationRestartInhibition {
        metadata workStatus : ModelingMetadata::StatusInfo { status = ModelingMetadata::StatusKind::open; }
        doc /* Motor restart shall remain inhibited after local isolation until deliberate local reset. */
        comment conditions /*
         *  Apply the S-003 qualification conditions for this criterion. Explicit mode coverage and independent shared obligations stated in S-113 continue to govern. */
    }
    requirement isolationRestartInhibition : IsolationRestartInhibition;
    #refinement dependency decomposeIsolationRestartInhibition from BlueDogRequirements::isolationRestartInhibition to BlueDogRequirements::emergencyControl {
        metadata workStatus : ModelingMetadata::StatusInfo { status = ModelingMetadata::StatusKind::open; }
        metadata rationale : ModelingMetadata::Rationale { text = "S-113 specifies a detailed acceptance condition for S-003 within their stated applicability. Selected limits, mechanisms and campaign conditions remain independent allocations; refinement makes no satisfaction implication or automatic parent-coverage claim."; }
    }

    requirement def <'S-114'> ManualControlLossShutdown {
        metadata workStatus : ModelingMetadata::StatusInfo { status = ModelingMetadata::StatusKind::open; }
        doc /* After remote control has been lost for 5 seconds during manual powered recovery, the vessel shall command zero thrust within a further 1 second. */
        comment conditions /*
         *  Apply the S-003 qualification conditions for this criterion. Explicit mode coverage and independent shared obligations stated in S-114 continue to govern. */
    }
    requirement manualControlLossShutdown : ManualControlLossShutdown;
    #refinement dependency decomposeManualControlLossShutdown from BlueDogRequirements::manualControlLossShutdown to BlueDogRequirements::emergencyControl {
        metadata workStatus : ModelingMetadata::StatusInfo { status = ModelingMetadata::StatusKind::open; }
        metadata rationale : ModelingMetadata::Rationale { text = "S-114 specifies a detailed acceptance condition for S-003 within their stated applicability. Selected limits, mechanisms and campaign conditions remain independent allocations; refinement makes no satisfaction implication or automatic parent-coverage claim."; }
    }

    requirement def <'S-115'> ControlLossLocationContinuity {
        metadata workStatus : ModelingMetadata::StatusInfo { status = ModelingMetadata::StatusKind::open; }
        doc /* Location reporting shall continue at the active telemetry cadence after remote-control loss whenever a telemetry link is available. */
        comment conditions /*
         *  Apply the S-003 qualification conditions for this criterion. Explicit mode coverage and independent shared obligations stated in S-115 continue to govern. */
    }
    requirement controlLossLocationContinuity : ControlLossLocationContinuity;
    #refinement dependency decomposeControlLossLocationContinuity from BlueDogRequirements::controlLossLocationContinuity to BlueDogRequirements::emergencyControl {
        metadata workStatus : ModelingMetadata::StatusInfo { status = ModelingMetadata::StatusKind::open; }
        metadata rationale : ModelingMetadata::Rationale { text = "S-115 specifies a detailed acceptance condition for S-003 within their stated applicability. Selected limits, mechanisms and campaign conditions remain independent allocations; refinement makes no satisfaction implication or automatic parent-coverage claim."; }
    }

    requirement def <'S-116'> NavigationLightPresentation {
        metadata workStatus : ModelingMetadata::StatusInfo { status = ModelingMetadata::StatusKind::open; }
        doc /* The vessel shall present the lights prescribed for its current mode by the S-004 compliance matrix without a person aboard. */
        comment conditions /*
         *  Apply the S-004 qualification conditions for this criterion. Explicit mode coverage and independent shared obligations stated in S-116 continue to govern. */
    }
    requirement navigationLightPresentation : NavigationLightPresentation;

    #derivation connection decomposeNavigationLightPresentation {
        metadata workStatus : ModelingMetadata::StatusInfo { status = ModelingMetadata::StatusKind::open; }
        metadata rationale : ModelingMetadata::Rationale { text = "This leaf isolates one acceptance outcome of S-004; the parent supplies shared verification conditions."; }
        end #original source ::> navigationConspicuity;
        end #derive target ::> navigationLightPresentation;
    }

    requirement def <'S-117'> NavigationShapePresentation {
        metadata workStatus : ModelingMetadata::StatusInfo { status = ModelingMetadata::StatusKind::open; }
        doc /* The vessel shall present the shapes prescribed for its current mode by the S-004 compliance matrix without a person aboard. */
        comment conditions /*
         *  Apply the S-004 qualification conditions for this criterion. Explicit mode coverage and independent shared obligations stated in S-117 continue to govern. */
    }
    requirement navigationShapePresentation : NavigationShapePresentation;

    #derivation connection decomposeNavigationShapePresentation {
        metadata workStatus : ModelingMetadata::StatusInfo { status = ModelingMetadata::StatusKind::open; }
        metadata rationale : ModelingMetadata::Rationale { text = "This leaf isolates one acceptance outcome of S-004; the parent supplies shared verification conditions."; }
        end #original source ::> navigationConspicuity;
        end #derive target ::> navigationShapePresentation;
    }

    requirement def <'S-118'> NavigationSoundPresentation {
        metadata workStatus : ModelingMetadata::StatusInfo { status = ModelingMetadata::StatusKind::open; }
        doc /* The vessel shall present the sound signals prescribed for its current mode by the S-004 compliance matrix without a person aboard. */
        comment conditions /*
         *  Apply the S-004 qualification conditions for this criterion. Explicit mode coverage and independent shared obligations stated in S-118 continue to govern. */
    }
    requirement navigationSoundPresentation : NavigationSoundPresentation;

    #derivation connection decomposeNavigationSoundPresentation {
        metadata workStatus : ModelingMetadata::StatusInfo { status = ModelingMetadata::StatusKind::open; }
        metadata rationale : ModelingMetadata::Rationale { text = "This leaf isolates one acceptance outcome of S-004; the parent supplies shared verification conditions."; }
        end #original source ::> navigationConspicuity;
        end #derive target ::> navigationSoundPresentation;
    }

    requirement def <'S-119'> SignalingModeDeadline {
        metadata workStatus : ModelingMetadata::StatusInfo { status = ModelingMetadata::StatusKind::open; }
        doc /* A commanded mode change shall select the corresponding signaling configuration within 1 second. */
        comment conditions /*
         *  Apply the S-004 qualification conditions for this criterion. Explicit mode coverage and independent shared obligations stated in S-119 continue to govern. */
    }
    requirement signalingModeDeadline : SignalingModeDeadline;
    #refinement dependency decomposeSignalingModeDeadline from BlueDogRequirements::signalingModeDeadline to BlueDogRequirements::navigationConspicuity {
        metadata workStatus : ModelingMetadata::StatusInfo { status = ModelingMetadata::StatusKind::open; }
        metadata rationale : ModelingMetadata::Rationale { text = "S-119 specifies a detailed acceptance condition for S-004 within their stated applicability. Selected limits, mechanisms and campaign conditions remain independent allocations; refinement makes no satisfaction implication or automatic parent-coverage claim."; }
    }

    requirement def <'S-120'> SignalingFaultRecording {
        metadata workStatus : ModelingMetadata::StatusInfo { status = ModelingMetadata::StatusKind::open; }
        doc /* Each detectable signaling failure shall be logged within 5 seconds of detection. */
        comment conditions /*
         *  Apply the S-004 qualification conditions for this criterion. Explicit mode coverage and independent shared obligations stated in S-120 continue to govern. */
    }
    requirement signalingFaultRecording : SignalingFaultRecording;
    #refinement dependency decomposeSignalingFaultRecording from BlueDogRequirements::signalingFaultRecording to BlueDogRequirements::navigationConspicuity {
        metadata workStatus : ModelingMetadata::StatusInfo { status = ModelingMetadata::StatusKind::open; }
        metadata rationale : ModelingMetadata::Rationale { text = "S-120 specifies a detailed acceptance condition for S-004 within their stated applicability. Selected limits, mechanisms and campaign conditions remain independent allocations; refinement makes no satisfaction implication or automatic parent-coverage claim."; }
    }

    requirement def <'S-121'> SignalingFaultReporting {
        metadata workStatus : ModelingMetadata::StatusInfo { status = ModelingMetadata::StatusKind::open; }
        doc /* With a functioning link, each detected signaling failure shall be reported to shore within 5 seconds. */
        comment conditions /*
         *  Apply the S-004 qualification conditions for this criterion. Explicit mode coverage and independent shared obligations stated in S-121 continue to govern. */
    }
    requirement signalingFaultReporting : SignalingFaultReporting;
    #refinement dependency decomposeSignalingFaultReporting from BlueDogRequirements::signalingFaultReporting to BlueDogRequirements::navigationConspicuity {
        metadata workStatus : ModelingMetadata::StatusInfo { status = ModelingMetadata::StatusKind::open; }
        metadata rationale : ModelingMetadata::Rationale { text = "S-121 specifies a detailed acceptance condition for S-004 within their stated applicability. Selected limits, mechanisms and campaign conditions remain independent allocations; refinement makes no satisfaction implication or automatic parent-coverage claim."; }
    }

    requirement def <'S-122'> DeploymentComplianceRecord {
        metadata workStatus : ModelingMetadata::StatusInfo { status = ModelingMetadata::StatusKind::open; }
        doc /* Each deployment shall have a dated compliance record identifying the craft, dimensions, waters, operating modes, applicable navigation and radio obligations, and permission evidence. */
        comment conditions /*
         *  Apply the S-005 qualification conditions for this criterion. Explicit mode coverage and independent shared obligations stated in S-122 continue to govern. */
    }
    requirement deploymentComplianceRecord : DeploymentComplianceRecord;
    #refinement dependency decomposeDeploymentComplianceRecord from BlueDogRequirements::deploymentComplianceRecord to BlueDogRequirements::regulatoryClassification {
        metadata workStatus : ModelingMetadata::StatusInfo { status = ModelingMetadata::StatusKind::open; }
        metadata rationale : ModelingMetadata::Rationale { text = "S-122 specifies a detailed acceptance condition for S-005 within their stated applicability. Selected limits, mechanisms and campaign conditions remain independent allocations; refinement makes no satisfaction implication or automatic parent-coverage claim."; }
    }

    requirement def <'S-123'> DeploymentReleaseGate {
        metadata workStatus : ModelingMetadata::StatusInfo { status = ModelingMetadata::StatusKind::open; }
        doc /* Deployment release shall be withheld while any mandatory authorization is absent, expired or unresolved. */
        comment conditions /*
         *  Apply the S-005 qualification conditions for this criterion. Explicit mode coverage and independent shared obligations stated in S-123 continue to govern. */
    }
    requirement deploymentReleaseGate : DeploymentReleaseGate;

    #derivation connection decomposeDeploymentReleaseGate {
        metadata workStatus : ModelingMetadata::StatusInfo { status = ModelingMetadata::StatusKind::open; }
        metadata rationale : ModelingMetadata::Rationale { text = "This leaf isolates one acceptance outcome of S-005; the parent supplies shared verification conditions."; }
        end #original source ::> regulatoryClassification;
        end #derive target ::> deploymentReleaseGate;
    }

    requirement def <'C-201'> TelemetryDisplayContent {
        metadata workStatus : ModelingMetadata::StatusInfo { status = ModelingMetadata::StatusKind::open; }
        doc /* The shore endpoint shall display UTC sample time, position, mode, conservative usable energy, reserve, faults and age from each current telemetry record. */
        comment conditions /*
         *  Apply the C-101 qualification conditions for this criterion. Explicit mode coverage and independent shared obligations stated in C-201 continue to govern. */
    }
    requirement telemetryDisplayContent : TelemetryDisplayContent;
    #refinement dependency decomposeTelemetryDisplayContent from BlueDogRequirements::telemetryDisplayContent to BlueDogRequirements::telemetryEquipment {
        metadata workStatus : ModelingMetadata::StatusInfo { status = ModelingMetadata::StatusKind::open; }
        metadata rationale : ModelingMetadata::Rationale { text = "C-201 specifies a detailed acceptance condition for C-101 within their stated applicability. Selected limits, mechanisms and campaign conditions remain independent allocations; refinement makes no satisfaction implication or automatic parent-coverage claim."; }
    }

    requirement def <'C-202'> TelemetryStaleIndication {
        metadata workStatus : ModelingMetadata::StatusInfo { status = ModelingMetadata::StatusKind::open; }
        doc /* The shore endpoint shall indicate stale data when record age exceeds its C-101 mode threshold until receipt of a record within its applicable threshold. */
        comment conditions /*
         *  Apply the C-101 qualification conditions for this criterion. Explicit mode coverage and independent shared obligations stated in C-202 continue to govern. */
    }
    requirement telemetryStaleIndication : TelemetryStaleIndication;
    #refinement dependency decomposeTelemetryStaleIndication from BlueDogRequirements::telemetryStaleIndication to BlueDogRequirements::telemetryEquipment {
        metadata workStatus : ModelingMetadata::StatusInfo { status = ModelingMetadata::StatusKind::open; }
        metadata rationale : ModelingMetadata::Rationale { text = "C-202 specifies a detailed acceptance condition for C-101 within their stated applicability. Selected limits, mechanisms and campaign conditions remain independent allocations; refinement makes no satisfaction implication or automatic parent-coverage claim."; }
    }

    requirement def <'C-203'> TelemetryIdentityPreservation {
        metadata workStatus : ModelingMetadata::StatusInfo { status = ModelingMetadata::StatusKind::open; }
        doc /* The shore endpoint shall preserve received record identity and sequence numbers across the C-101 outage/reconnection test. */
        comment conditions /*
         *  Apply the C-101 qualification conditions for this criterion. Explicit mode coverage and independent shared obligations stated in C-203 continue to govern. */
    }
    requirement telemetryIdentityPreservation : TelemetryIdentityPreservation;
    #refinement dependency decomposeTelemetryIdentityPreservation from BlueDogRequirements::telemetryIdentityPreservation to BlueDogRequirements::telemetryEquipment {
        metadata workStatus : ModelingMetadata::StatusInfo { status = ModelingMetadata::StatusKind::open; }
        metadata rationale : ModelingMetadata::Rationale { text = "C-203 specifies a detailed acceptance condition for C-101 within their stated applicability. Selected limits, mechanisms and campaign conditions remain independent allocations; refinement makes no satisfaction implication or automatic parent-coverage claim."; }
    }

    requirement def <'C-204'> TelemetryDuplicateSuppression {
        metadata workStatus : ModelingMetadata::StatusInfo { status = ModelingMetadata::StatusKind::open; }
        doc /* The shore endpoint shall not present a duplicate telemetry record as a new observation. */
        comment conditions /*
         *  Apply the C-101 qualification conditions for this criterion. Explicit mode coverage and independent shared obligations stated in C-204 continue to govern. */
    }
    requirement telemetryDuplicateSuppression : TelemetryDuplicateSuppression;
    #refinement dependency decomposeTelemetryDuplicateSuppression from BlueDogRequirements::telemetryDuplicateSuppression to BlueDogRequirements::telemetryEquipment {
        metadata workStatus : ModelingMetadata::StatusInfo { status = ModelingMetadata::StatusKind::open; }
        metadata rationale : ModelingMetadata::Rationale { text = "C-204 specifies a detailed acceptance condition for C-101 within their stated applicability. Selected limits, mechanisms and campaign conditions remain independent allocations; refinement makes no satisfaction implication or automatic parent-coverage claim."; }
    }

    requirement def <'C-205'> UnauthenticatedCommandRejection {
        metadata workStatus : ModelingMetadata::StatusInfo { status = ModelingMetadata::StatusKind::open; }
        doc /* Commands failing authentication shall cause zero accepted actuator or mission-state changes. */
        comment conditions /*
         *  Apply the C-102 qualification conditions for this criterion. Explicit mode coverage and independent shared obligations stated in C-205 continue to govern. */
    }
    requirement unauthenticatedCommandRejection : UnauthenticatedCommandRejection;
    #refinement dependency decomposeUnauthenticatedCommandRejection from BlueDogRequirements::unauthenticatedCommandRejection to BlueDogRequirements::commandIntegrity {
        metadata workStatus : ModelingMetadata::StatusInfo { status = ModelingMetadata::StatusKind::open; }
        metadata rationale : ModelingMetadata::Rationale { text = "C-205 specifies a detailed acceptance condition for C-102 within their stated applicability. Selected limits, mechanisms and campaign conditions remain independent allocations; refinement makes no satisfaction implication or automatic parent-coverage claim."; }
    }

    requirement def <'C-206'> ReplayCommandRejection {
        metadata workStatus : ModelingMetadata::StatusInfo { status = ModelingMetadata::StatusKind::open; }
        doc /* Commands with previously used sequence numbers shall cause zero accepted actuator or mission-state changes. */
        comment conditions /*
         *  Apply the C-102 qualification conditions for this criterion. Explicit mode coverage and independent shared obligations stated in C-206 continue to govern. */
    }
    requirement replayCommandRejection : ReplayCommandRejection;
    #refinement dependency decomposeReplayCommandRejection from BlueDogRequirements::replayCommandRejection to BlueDogRequirements::commandIntegrity {
        metadata workStatus : ModelingMetadata::StatusInfo { status = ModelingMetadata::StatusKind::open; }
        metadata rationale : ModelingMetadata::Rationale { text = "C-206 specifies a detailed acceptance condition for C-102 within their stated applicability. Selected limits, mechanisms and campaign conditions remain independent allocations; refinement makes no satisfaction implication or automatic parent-coverage claim."; }
    }

    requirement def <'C-207'> ExpiredCommandRejection {
        metadata workStatus : ModelingMetadata::StatusInfo { status = ModelingMetadata::StatusKind::open; }
        doc /* Commands older than 30 seconds shall cause zero accepted actuator or mission-state changes. */
        comment conditions /*
         *  Apply the C-102 qualification conditions for this criterion. Explicit mode coverage and independent shared obligations stated in C-207 continue to govern. */
    }
    requirement expiredCommandRejection : ExpiredCommandRejection;
    #refinement dependency decomposeExpiredCommandRejection from BlueDogRequirements::expiredCommandRejection to BlueDogRequirements::commandIntegrity {
        metadata workStatus : ModelingMetadata::StatusInfo { status = ModelingMetadata::StatusKind::open; }
        metadata rationale : ModelingMetadata::Rationale { text = "C-207 specifies a detailed acceptance condition for C-102 within their stated applicability. Selected limits, mechanisms and campaign conditions remain independent allocations; refinement makes no satisfaction implication or automatic parent-coverage claim."; }
    }

    requirement def <'C-208'> AcceptedCommandDeadline {
        metadata workStatus : ModelingMetadata::StatusInfo { status = ModelingMetadata::StatusKind::open; }
        doc /* An accepted abort or mode-change command shall be applied within 1 second of complete receipt. */
        comment conditions /*
         *  Apply the C-102 qualification conditions for this criterion. Explicit mode coverage and independent shared obligations stated in C-208 continue to govern. */
    }
    requirement acceptedCommandDeadline : AcceptedCommandDeadline;
    #refinement dependency decomposeAcceptedCommandDeadline from BlueDogRequirements::acceptedCommandDeadline to BlueDogRequirements::commandIntegrity {
        metadata workStatus : ModelingMetadata::StatusInfo { status = ModelingMetadata::StatusKind::open; }
        metadata rationale : ModelingMetadata::Rationale { text = "C-208 specifies a detailed acceptance condition for C-102 within their stated applicability. Selected limits, mechanisms and campaign conditions remain independent allocations; refinement makes no satisfaction implication or automatic parent-coverage claim."; }
    }

    requirement def <'C-209'> OnboardAcknowledgmentDeadline {
        metadata workStatus : ModelingMetadata::StatusInfo { status = ModelingMetadata::StatusKind::open; }
        doc /* An accepted abort or mode-change command shall be acknowledged onboard within 1 second of complete receipt. */
        comment conditions /*
         *  Apply the C-102 qualification conditions for this criterion. Explicit mode coverage and independent shared obligations stated in C-209 continue to govern. */
    }
    requirement onboardAcknowledgmentDeadline : OnboardAcknowledgmentDeadline;
    #refinement dependency decomposeOnboardAcknowledgmentDeadline from BlueDogRequirements::onboardAcknowledgmentDeadline to BlueDogRequirements::commandIntegrity {
        metadata workStatus : ModelingMetadata::StatusInfo { status = ModelingMetadata::StatusKind::open; }
        metadata rationale : ModelingMetadata::Rationale { text = "C-209 specifies a detailed acceptance condition for C-102 within their stated applicability. Selected limits, mechanisms and campaign conditions remain independent allocations; refinement makes no satisfaction implication or automatic parent-coverage claim."; }
    }

    requirement def <'C-210'> AcknowledgmentQueueing {
        metadata workStatus : ModelingMetadata::StatusInfo { status = ModelingMetadata::StatusKind::open; }
        doc /* An accepted command acknowledgment shall enter the transmit queue in the same command-processing cycle when a link is available. */
        comment conditions /*
         *  Apply the C-102 qualification conditions for this criterion. Explicit mode coverage and independent shared obligations stated in C-210 continue to govern. */
    }
    requirement acknowledgmentQueueing : AcknowledgmentQueueing;
    #refinement dependency decomposeAcknowledgmentQueueing from BlueDogRequirements::acknowledgmentQueueing to BlueDogRequirements::commandIntegrity {
        metadata workStatus : ModelingMetadata::StatusInfo { status = ModelingMetadata::StatusKind::open; }
        metadata rationale : ModelingMetadata::Rationale { text = "C-210 specifies a detailed acceptance condition for C-102 within their stated applicability. Selected limits, mechanisms and campaign conditions remain independent allocations; refinement makes no satisfaction implication or automatic parent-coverage claim."; }
    }

    requirement def <'C-211'> ExternalControlDisqualification {
        metadata workStatus : ModelingMetadata::StatusInfo { status = ModelingMetadata::StatusKind::open; }
        doc /* Acceptance of external mission or steering control during a qualifying attempt shall permanently disqualify that attempt. */
        comment conditions /*
         *  Apply the C-102 qualification conditions for this criterion. Explicit mode coverage and independent shared obligations stated in C-211 continue to govern. */
    }
    requirement externalControlDisqualification : ExternalControlDisqualification;
    #refinement dependency decomposeExternalControlDisqualification from BlueDogRequirements::externalControlDisqualification to BlueDogRequirements::commandIntegrity {
        metadata workStatus : ModelingMetadata::StatusInfo { status = ModelingMetadata::StatusKind::open; }
        metadata rationale : ModelingMetadata::Rationale { text = "C-211 specifies a detailed acceptance condition for C-102 within their stated applicability. Selected limits, mechanisms and campaign conditions remain independent allocations; refinement makes no satisfaction implication or automatic parent-coverage claim."; }
    }

    requirement def <'N-101'> VisibilityNavigationCapability {
        metadata workStatus : ModelingMetadata::StatusInfo { status = ModelingMetadata::StatusKind::open; }
        doc /* Navigation shall meet E-002 and E-008 acceptance criteria at visibility of at least 1 km in daylight and darkness. */
        comment conditions /*
         *  Apply the N-033 qualification conditions for this criterion. Explicit mode coverage and independent shared obligations stated in N-101 continue to govern. */
    }
    requirement visibilityNavigationCapability : VisibilityNavigationCapability;

    #derivation connection decomposeVisibilityNavigationCapability {
        metadata workStatus : ModelingMetadata::StatusInfo { status = ModelingMetadata::StatusKind::open; }
        metadata rationale : ModelingMetadata::Rationale { text = "This leaf isolates one acceptance outcome of N-033; the parent supplies shared verification conditions."; }
        end #original source ::> visibility;
        end #derive target ::> visibilityNavigationCapability;
    }

    requirement def <'N-102'> VisibilityTrafficCapability {
        metadata workStatus : ModelingMetadata::StatusInfo { status = ModelingMetadata::StatusKind::open; }
        doc /* Traffic assessment shall meet the reviewed class-specific S-001 criteria at visibility of at least 1 km in daylight and darkness.*/
        comment conditions /*
         *  Apply the N-033 qualification conditions for this criterion. Explicit mode coverage and independent shared obligations stated in N-102 continue to govern. */
    }
    requirement visibilityTrafficCapability : VisibilityTrafficCapability;

    #derivation connection decomposeVisibilityTrafficCapability {
        metadata workStatus : ModelingMetadata::StatusInfo { status = ModelingMetadata::StatusKind::open; }
        metadata rationale : ModelingMetadata::Rationale { text = "This leaf isolates one acceptance outcome of N-033; the parent supplies shared verification conditions."; }
        end #original source ::> visibility;
        end #derive target ::> visibilityTrafficCapability;
    }

    requirement def <'N-103'> RestrictedVisibilityEntry {
        metadata workStatus : ModelingMetadata::StatusInfo { status = ModelingMetadata::StatusKind::open; }
        doc /* On detecting visibility below 1 km, the vessel shall enter restricted-visibility state within 60 seconds. */
        comment conditions /*
         *  Apply the N-033 qualification conditions for this criterion. Explicit mode coverage and independent shared obligations stated in N-103 continue to govern. */
    }
    requirement restrictedVisibilityEntry : RestrictedVisibilityEntry;
    #refinement dependency decomposeRestrictedVisibilityEntry from BlueDogRequirements::restrictedVisibilityEntry to BlueDogRequirements::visibility {
        metadata workStatus : ModelingMetadata::StatusInfo { status = ModelingMetadata::StatusKind::open; }
        metadata rationale : ModelingMetadata::Rationale { text = "N-103 specifies a detailed acceptance condition for N-033 within their stated applicability. Selected limits, mechanisms and campaign conditions remain independent allocations; refinement makes no satisfaction implication or automatic parent-coverage claim."; }
    }

    requirement def <'N-104'> RestrictedVisibilityEvidence {
        metadata workStatus : ModelingMetadata::StatusInfo { status = ModelingMetadata::StatusKind::open; }
        doc /* Restricted-visibility operation shall be recorded as outside the normal operational envelope. */
        comment conditions /*
         *  Apply the N-033 qualification conditions for this criterion. Explicit mode coverage and independent shared obligations stated in N-104 continue to govern. */
    }
    requirement restrictedVisibilityEvidence : RestrictedVisibilityEvidence;
    #refinement dependency decomposeRestrictedVisibilityEvidence from BlueDogRequirements::restrictedVisibilityEvidence to BlueDogRequirements::visibility {
        metadata workStatus : ModelingMetadata::StatusInfo { status = ModelingMetadata::StatusKind::open; }
        metadata rationale : ModelingMetadata::Rationale { text = "N-104 specifies a detailed acceptance condition for N-033 within their stated applicability. Selected limits, mechanisms and campaign conditions remain independent allocations; refinement makes no satisfaction implication or automatic parent-coverage claim."; }
    }

    requirement def <'N-105'> RestrictedVisibilityCollisionAssessment {
        metadata workStatus : ModelingMetadata::StatusInfo { status = ModelingMetadata::StatusKind::open; }
        doc /* Collision assessment shall remain active during restricted-visibility operation. */
        comment conditions /*
         *  Apply the N-033 qualification conditions for this criterion. Explicit mode coverage and independent shared obligations stated in N-105 continue to govern. */
    }
    requirement restrictedVisibilityCollisionAssessment : RestrictedVisibilityCollisionAssessment;

    #derivation connection decomposeRestrictedVisibilityCollisionAssessment {
        metadata workStatus : ModelingMetadata::StatusInfo { status = ModelingMetadata::StatusKind::open; }
        metadata rationale : ModelingMetadata::Rationale { text = "This leaf isolates one acceptance outcome of N-033; the parent supplies shared verification conditions."; }
        end #original source ::> visibility;
        end #derive target ::> restrictedVisibilityCollisionAssessment;
    }

    requirement def <'N-106'> SurvivalEntryDeadline {
        metadata workStatus : ModelingMetadata::StatusInfo { status = ModelingMetadata::StatusKind::open; }
        doc /* The vessel shall enter survival mode within 60 seconds of the N-035 upper-limit trigger. */
        comment conditions /*
         *  Apply the N-035 qualification conditions for this criterion. Explicit mode coverage and independent shared obligations stated in N-106 continue to govern. */
    }
    requirement survivalEntryDeadline : SurvivalEntryDeadline;
    #refinement dependency decomposeSurvivalEntryDeadline from BlueDogRequirements::survivalEntryDeadline to BlueDogRequirements::envelopeTransition {
        metadata workStatus : ModelingMetadata::StatusInfo { status = ModelingMetadata::StatusKind::open; }
        metadata rationale : ModelingMetadata::Rationale { text = "N-106 specifies a detailed acceptance condition for N-035 within their stated applicability. Selected limits, mechanisms and campaign conditions remain independent allocations; refinement makes no satisfaction implication or automatic parent-coverage claim."; }
    }

    requirement def <'N-107'> SurvivalTransitionRecording {
        metadata workStatus : ModelingMetadata::StatusInfo { status = ModelingMetadata::StatusKind::open; }
        doc /* Every survival-mode entry shall have a corresponding event record. */
        comment conditions /*
         *  Apply the N-035 qualification conditions for this criterion. Explicit mode coverage and independent shared obligations stated in N-107 continue to govern. */
    }
    requirement survivalTransitionRecording : SurvivalTransitionRecording;
    #refinement dependency decomposeSurvivalTransitionRecording from BlueDogRequirements::survivalTransitionRecording to BlueDogRequirements::envelopeTransition {
        metadata workStatus : ModelingMetadata::StatusInfo { status = ModelingMetadata::StatusKind::open; }
        metadata rationale : ModelingMetadata::Rationale { text = "N-107 specifies a detailed acceptance condition for N-035 within their stated applicability. Selected limits, mechanisms and campaign conditions remain independent allocations; refinement makes no satisfaction implication or automatic parent-coverage claim."; }
    }

    requirement def <'N-108'> SailingResumptionDeadline {
        metadata workStatus : ModelingMetadata::StatusInfo { status = ModelingMetadata::StatusKind::open; }
        doc /* Full autonomous sailing shall resume within 5 minutes of N-035 resumption eligibility becoming continuously true. */
        comment conditions /*
         *  Apply the N-035 qualification conditions for this criterion. Explicit mode coverage and independent shared obligations stated in N-108 continue to govern. */
    }
    requirement sailingResumptionDeadline : SailingResumptionDeadline;
    #refinement dependency decomposeSailingResumptionDeadline from BlueDogRequirements::sailingResumptionDeadline to BlueDogRequirements::envelopeTransition {
        metadata workStatus : ModelingMetadata::StatusInfo { status = ModelingMetadata::StatusKind::open; }
        metadata rationale : ModelingMetadata::Rationale { text = "N-108 specifies a detailed acceptance condition for N-035 within their stated applicability. Selected limits, mechanisms and campaign conditions remain independent allocations; refinement makes no satisfaction implication or automatic parent-coverage claim."; }
    }

    requirement def <'N-109'> SailingResumptionInhibition {
        metadata workStatus : ModelingMetadata::StatusInfo { status = ModelingMetadata::StatusKind::open; }
        doc /* Full autonomous sailing shall remain inhibited while N-035 resumption eligibility is false. */
        comment conditions /*
         *  Apply the N-035 qualification conditions for this criterion. Explicit mode coverage and independent shared obligations stated in N-109 continue to govern. */
    }
    requirement sailingResumptionInhibition : SailingResumptionInhibition;

    #derivation connection decomposeSailingResumptionInhibition {
        metadata workStatus : ModelingMetadata::StatusInfo { status = ModelingMetadata::StatusKind::open; }
        metadata rationale : ModelingMetadata::Rationale { text = "This leaf isolates one acceptance outcome of N-035; the parent supplies shared verification conditions."; }
        end #original source ::> envelopeTransition;
        end #derive target ::> sailingResumptionInhibition;
    }

    requirement def <'N-110'> ResumptionBlockEvidence {
        metadata workStatus : ModelingMetadata::StatusInfo { status = ModelingMetadata::StatusKind::open; }
        doc /* Every blocked sailing-resumption attempt shall record the blocking condition. */
        comment conditions /*
         *  Apply the N-035 qualification conditions for this criterion. Explicit mode coverage and independent shared obligations stated in N-110 continue to govern. */
    }
    requirement resumptionBlockEvidence : ResumptionBlockEvidence;
    #refinement dependency decomposeResumptionBlockEvidence from BlueDogRequirements::resumptionBlockEvidence to BlueDogRequirements::envelopeTransition {
        metadata workStatus : ModelingMetadata::StatusInfo { status = ModelingMetadata::StatusKind::open; }
        metadata rationale : ModelingMetadata::Rationale { text = "N-110 specifies a detailed acceptance condition for N-035 within their stated applicability. Selected limits, mechanisms and campaign conditions remain independent allocations; refinement makes no satisfaction implication or automatic parent-coverage claim."; }
    }

    requirement def <'N-111'> WetMechanismTravel {
        metadata workStatus : ModelingMetadata::StatusInfo { status = ModelingMetadata::StatusKind::open; }
        doc /* After each N-044 exposure, external mechanisms shall complete their full commanded travel without seizure. */
        comment conditions /*
         *  Apply the N-044 qualification conditions for this criterion. Explicit mode coverage and independent shared obligations stated in N-111 continue to govern. */
    }
    requirement wetMechanismTravel : WetMechanismTravel;
    #refinement dependency decomposeWetMechanismTravel from BlueDogRequirements::wetMechanismTravel to BlueDogRequirements::wetMechanicalIntegrity {
        metadata workStatus : ModelingMetadata::StatusInfo { status = ModelingMetadata::StatusKind::open; }
        metadata rationale : ModelingMetadata::Rationale { text = "N-111 specifies a detailed acceptance condition for N-044 within their stated applicability. Selected limits, mechanisms and campaign conditions remain independent allocations; refinement makes no satisfaction implication or automatic parent-coverage claim."; }
    }

    requirement def <'N-112'> WetJointIntegrity {
        metadata workStatus : ModelingMetadata::StatusInfo { status = ModelingMetadata::StatusKind::open; }
        doc /* After each N-044 exposure, structural joints shall show no separation or through-cracks on visual inspection at 5 times magnification. */
        comment conditions /*
         *  Apply the N-044 qualification conditions for this criterion. Explicit mode coverage and independent shared obligations stated in N-112 continue to govern. */
    }
    requirement wetJointIntegrity : WetJointIntegrity;
    #refinement dependency decomposeWetJointIntegrity from BlueDogRequirements::wetJointIntegrity to BlueDogRequirements::wetMechanicalIntegrity {
        metadata workStatus : ModelingMetadata::StatusInfo { status = ModelingMetadata::StatusKind::open; }
        metadata rationale : ModelingMetadata::Rationale { text = "N-112 specifies a detailed acceptance condition for N-044 within their stated applicability. Selected limits, mechanisms and campaign conditions remain independent allocations; refinement makes no satisfaction implication or automatic parent-coverage claim."; }
    }

    requirement def <'N-113'> WetConductorResistance {
        metadata workStatus : ModelingMetadata::StatusInfo { status = ModelingMetadata::StatusKind::open; }
        doc /* After each N-045 exposure, end-to-end conductor resistance shall be no more than 10 percent above its pre-test value. */
        comment conditions /*
         *  Apply the N-045 qualification conditions for this criterion. Explicit mode coverage and independent shared obligations stated in N-113 continue to govern. */
    }
    requirement wetConductorResistance : WetConductorResistance;
    #refinement dependency decomposeWetConductorResistance from BlueDogRequirements::wetConductorResistance to BlueDogRequirements::wetElectricalIntegrity {
        metadata workStatus : ModelingMetadata::StatusInfo { status = ModelingMetadata::StatusKind::open; }
        metadata rationale : ModelingMetadata::Rationale { text = "N-113 specifies a detailed acceptance condition for N-045 within their stated applicability. Selected limits, mechanisms and campaign conditions remain independent allocations; refinement makes no satisfaction implication or automatic parent-coverage claim."; }
    }

    requirement def <'N-114'> WetInsulationResistance {
        metadata workStatus : ModelingMetadata::StatusInfo { status = ModelingMetadata::StatusKind::open; }
        doc /* After each N-045 exposure, conductor-to-conductor and conductor-to-case insulation resistance shall be at least 1 megohm at 50 V DC. */
        comment conditions /*
         *  Apply the N-045 qualification conditions for this criterion. Explicit mode coverage and independent shared obligations stated in N-114 continue to govern. */
    }
    requirement wetInsulationResistance : WetInsulationResistance;
    #refinement dependency decomposeWetInsulationResistance from BlueDogRequirements::wetInsulationResistance to BlueDogRequirements::wetElectricalIntegrity {
        metadata workStatus : ModelingMetadata::StatusInfo { status = ModelingMetadata::StatusKind::open; }
        metadata rationale : ModelingMetadata::Rationale { text = "N-114 specifies a detailed acceptance condition for N-045 within their stated applicability. Selected limits, mechanisms and campaign conditions remain independent allocations; refinement makes no satisfaction implication or automatic parent-coverage claim."; }
    }

    requirement def <'N-115'> HotSunElectronicsOperation {
        metadata workStatus : ModelingMetadata::StatusInfo { status = ModelingMetadata::StatusKind::open; }
        doc /* Powered electronics shall retain operational functions throughout the N-046 exposure. */
        comment conditions /*
         *  Apply the N-046 qualification conditions for this criterion. Explicit mode coverage and independent shared obligations stated in N-115 continue to govern. */
    }
    requirement hotSunElectronicsOperation : HotSunElectronicsOperation;

    #derivation connection decomposeHotSunElectronicsOperation {
        metadata workStatus : ModelingMetadata::StatusInfo { status = ModelingMetadata::StatusKind::open; }
        metadata rationale : ModelingMetadata::Rationale { text = "This leaf isolates one acceptance outcome of N-046; the parent supplies shared verification conditions."; }
        end #original source ::> solarHeating;
        end #derive target ::> hotSunElectronicsOperation;
    }

    requirement def <'N-116'> HotSunBatteryTemperature {
        metadata workStatus : ModelingMetadata::StatusInfo { status = ModelingMetadata::StatusKind::open; }
        doc /* Battery temperatures shall remain within manufacturer operating limits throughout the N-046 exposure. */
        comment conditions /*
         *  Apply the N-046 qualification conditions for this criterion. Explicit mode coverage and independent shared obligations stated in N-116 continue to govern. */
    }
    requirement hotSunBatteryTemperature : HotSunBatteryTemperature;

    #derivation connection decomposeHotSunBatteryTemperature {
        metadata workStatus : ModelingMetadata::StatusInfo { status = ModelingMetadata::StatusKind::open; }
        metadata rationale : ModelingMetadata::Rationale { text = "This leaf isolates one acceptance outcome of N-046; the parent supplies shared verification conditions."; }
        end #original source ::> solarHeating;
        end #derive target ::> hotSunBatteryTemperature;
    }

    requirement def <'N-117'> BatteryChargeTemperatureInhibition {
        metadata workStatus : ModelingMetadata::StatusInfo { status = ModelingMetadata::StatusKind::open; }
        doc /* Battery charging shall remain inhibited whenever measured battery temperature is outside the manufacturer permitted charge range. */
        comment conditions /*
         *  Apply the N-046 qualification conditions for this criterion. Explicit mode coverage and independent shared obligations stated in N-117 continue to govern. */
    }
    requirement batteryChargeTemperatureInhibition : BatteryChargeTemperatureInhibition;

    dependency decomposeBatteryChargeTemperatureInhibition from batteryChargeTemperatureInhibition to solarHeating {
        metadata rationale : ModelingMetadata::Rationale { text = "Charge-temperature protection applies beyond the solar-heating campaign. The campaign supplies one relevant verification exposure rather than the source of this universal battery-protection obligation."; }
    }

    requirement def <'N-118'> RightingDeadline {
        metadata workStatus : ModelingMetadata::StatusInfo { status = ModelingMetadata::StatusKind::open; }
        doc /* The vessel shall self-right within 60 seconds of each N-051 release. */
        attribute measuredRightingTime : TimeValue;
        require constraint rightingDeadline {
            measuredRightingTime >= 0 [s] and measuredRightingTime <= 60 [s]
        }
        comment conditions /*
         *  Apply the N-051 qualification conditions for this criterion. Explicit mode coverage and independent shared obligations stated in N-118 continue to govern. */
    }
    requirement rightingDeadline : RightingDeadline;

    #derivation connection decomposeRightingDeadline {
        metadata workStatus : ModelingMetadata::StatusInfo { status = ModelingMetadata::StatusKind::open; }
        metadata rationale : ModelingMetadata::Rationale { text = "This leaf isolates one acceptance outcome of N-051; the parent supplies shared verification conditions."; }
        end #original source ::> selfRighting;
        end #derive target ::> rightingDeadline;
    }

    requirement def <'N-119'> CapsizeRigRetention {
        metadata workStatus : ModelingMetadata::StatusInfo { status = ModelingMetadata::StatusKind::open; }
        doc /* The vessel shall retain its rig through every N-051 release. */
        comment conditions /*
         *  Apply the N-051 qualification conditions for this criterion. Explicit mode coverage and independent shared obligations stated in N-119 continue to govern. */
    }
    requirement capsizeRigRetention : CapsizeRigRetention;

    #derivation connection decomposeCapsizeRigRetention {
        metadata workStatus : ModelingMetadata::StatusInfo { status = ModelingMetadata::StatusKind::open; }
        metadata rationale : ModelingMetadata::Rationale { text = "This leaf isolates one acceptance outcome of N-051; the parent supplies shared verification conditions."; }
        end #original source ::> selfRighting;
        end #derive target ::> capsizeRigRetention;
    }

    requirement def <'N-120'> CapsizeBallastRetention {
        metadata workStatus : ModelingMetadata::StatusInfo { status = ModelingMetadata::StatusKind::open; }
        doc /* The vessel shall retain its ballast through every N-051 release. */
        comment conditions /*
         *  Apply the N-051 qualification conditions for this criterion. Explicit mode coverage and independent shared obligations stated in N-120 continue to govern. */
    }
    requirement capsizeBallastRetention : CapsizeBallastRetention;

    #derivation connection decomposeCapsizeBallastRetention {
        metadata workStatus : ModelingMetadata::StatusInfo { status = ModelingMetadata::StatusKind::open; }
        metadata rationale : ModelingMetadata::Rationale { text = "This leaf isolates one acceptance outcome of N-051; the parent supplies shared verification conditions."; }
        end #original source ::> selfRighting;
        end #derive target ::> capsizeBallastRetention;
    }

    requirement def <'N-121'> CapsizeElectronicsSealing {
        metadata workStatus : ModelingMetadata::StatusInfo { status = ModelingMetadata::StatusKind::open; }
        doc /* No water shall reach electronics during any N-051 release. */
        comment conditions /*
         *  Apply the N-051 qualification conditions for this criterion. Explicit mode coverage and independent shared obligations stated in N-121 continue to govern. */
    }
    requirement capsizeElectronicsSealing : CapsizeElectronicsSealing;

    #derivation connection decomposeCapsizeElectronicsSealing {
        metadata workStatus : ModelingMetadata::StatusInfo { status = ModelingMetadata::StatusKind::open; }
        metadata rationale : ModelingMetadata::Rationale { text = "This leaf isolates one acceptance outcome of N-051; the parent supplies shared verification conditions."; }
        end #original source ::> selfRighting;
        end #derive target ::> capsizeElectronicsSealing;
    }

    requirement def <'N-122'> ControlRecoveryDeadline {
        metadata workStatus : ModelingMetadata::StatusInfo { status = ModelingMetadata::StatusKind::open; }
        doc /* The vessel shall restore mode-appropriate autonomous sail/steering control within 120 seconds from each N-051 release. */
        attribute measuredControlRecoveryTime : TimeValue;
        require constraint controlRecoveryDeadline {
            measuredControlRecoveryTime >= 0 [s] and measuredControlRecoveryTime <= 120 [s]
        }
        comment conditions /*
         *  Apply the N-052 qualification conditions for this criterion. Explicit mode coverage and independent shared obligations stated in N-122 continue to govern. */
    }
    requirement controlRecoveryDeadline : ControlRecoveryDeadline;
    #refinement dependency decomposeControlRecoveryDeadline from BlueDogRequirements::controlRecoveryDeadline to BlueDogRequirements::capsizeControlRecovery {
        metadata workStatus : ModelingMetadata::StatusInfo { status = ModelingMetadata::StatusKind::open; }
        metadata rationale : ModelingMetadata::Rationale { text = "N-122 specifies a detailed acceptance condition for N-052 within their stated applicability. Selected limits, mechanisms and campaign conditions remain independent allocations; refinement makes no satisfaction implication or automatic parent-coverage claim."; }
    }

    requirement def <'N-123'> CapsizeGateProgressRetention {
        metadata workStatus : ModelingMetadata::StatusInfo { status = ModelingMetadata::StatusKind::open; }
        doc /* Gate progress shall be preserved through every N-051 release. */
        comment conditions /*
         *  Apply the N-052 qualification conditions for this criterion. Explicit mode coverage and independent shared obligations stated in N-123 continue to govern. */
    }
    requirement capsizeGateProgressRetention : CapsizeGateProgressRetention;
    #refinement dependency decomposeCapsizeGateProgressRetention from BlueDogRequirements::capsizeGateProgressRetention to BlueDogRequirements::capsizeControlRecovery {
        metadata workStatus : ModelingMetadata::StatusInfo { status = ModelingMetadata::StatusKind::open; }
        metadata rationale : ModelingMetadata::Rationale { text = "N-123 specifies a detailed acceptance condition for N-052 within their stated applicability. Selected limits, mechanisms and campaign conditions remain independent allocations; refinement makes no satisfaction implication or automatic parent-coverage claim."; }
    }

    requirement def <'N-124'> CapsizeQualificationRetention {
        metadata workStatus : ModelingMetadata::StatusInfo { status = ModelingMetadata::StatusKind::open; }
        doc /* Qualification status shall be preserved through every N-051 release absent an independently disqualifying event. */
        comment conditions /*
         *  Apply the N-052 qualification conditions for this criterion. Explicit mode coverage and independent shared obligations stated in N-124 continue to govern. */
    }
    requirement capsizeQualificationRetention : CapsizeQualificationRetention;
    #refinement dependency decomposeCapsizeQualificationRetention from BlueDogRequirements::capsizeQualificationRetention to BlueDogRequirements::capsizeControlRecovery {
        metadata workStatus : ModelingMetadata::StatusInfo { status = ModelingMetadata::StatusKind::open; }
        metadata rationale : ModelingMetadata::Rationale { text = "N-124 specifies a detailed acceptance condition for N-052 within their stated applicability. Selected limits, mechanisms and campaign conditions remain independent allocations; refinement makes no satisfaction implication or automatic parent-coverage claim."; }
    }

    requirement def <'N-125'> CapsizeRestrictionRetention {
        metadata workStatus : ModelingMetadata::StatusInfo { status = ModelingMetadata::StatusKind::open; }
        doc /* Control restoration after each N-051 release shall preserve every active survival, low-energy, recovery and motor-inhibition restriction. */
        comment conditions /*
         *  Apply the N-052 qualification conditions for this criterion. Explicit mode coverage and independent shared obligations stated in N-125 continue to govern. */
    }
    requirement capsizeRestrictionRetention : CapsizeRestrictionRetention;
    #refinement dependency decomposeCapsizeRestrictionRetention from BlueDogRequirements::capsizeRestrictionRetention to BlueDogRequirements::capsizeControlRecovery {
        metadata workStatus : ModelingMetadata::StatusInfo { status = ModelingMetadata::StatusKind::open; }
        metadata rationale : ModelingMetadata::Rationale { text = "N-125 specifies a detailed acceptance condition for N-052 within their stated applicability. Selected limits, mechanisms and campaign conditions remain independent allocations; refinement makes no satisfaction implication or automatic parent-coverage claim."; }
    }

    requirement def <'N-126'> WeedPassageSpeed {
        metadata workStatus : ModelingMetadata::StatusInfo { status = ModelingMetadata::StatusKind::open; }
        doc /* During each N-053 patch passage, mean water-relative sailing speed shall be at least 50 percent of the weed-free reference speed. */
        comment conditions /*
         *  Apply the N-053 qualification conditions for this criterion. Explicit mode coverage and independent shared obligations stated in N-126 continue to govern. */
    }
    requirement weedPassageSpeed : WeedPassageSpeed;
    #refinement dependency decomposeWeedPassageSpeed from BlueDogRequirements::weedPassageSpeed to BlueDogRequirements::submergedWeedPassage {
        metadata workStatus : ModelingMetadata::StatusInfo { status = ModelingMetadata::StatusKind::open; }
        metadata rationale : ModelingMetadata::Rationale { text = "N-126 specifies a detailed acceptance condition for N-053 within their stated applicability. Selected limits, mechanisms and campaign conditions remain independent allocations; refinement makes no satisfaction implication or automatic parent-coverage claim."; }
    }

    requirement def <'N-127'> WeedPassageSteering {
        metadata workStatus : ModelingMetadata::StatusInfo { status = ModelingMetadata::StatusKind::open; }
        doc /* After each N-053 patch passage, full commanded rudder travel shall be regained within 5 minutes. */
        comment conditions /*
         *  Apply the N-053 qualification conditions for this criterion. Explicit mode coverage and independent shared obligations stated in N-127 continue to govern. */
    }
    requirement weedPassageSteering : WeedPassageSteering;
    #refinement dependency decomposeWeedPassageSteering from BlueDogRequirements::weedPassageSteering to BlueDogRequirements::submergedWeedPassage {
        metadata workStatus : ModelingMetadata::StatusInfo { status = ModelingMetadata::StatusKind::open; }
        metadata rationale : ModelingMetadata::Rationale { text = "N-127 specifies a detailed acceptance condition for N-053 within their stated applicability. Selected limits, mechanisms and campaign conditions remain independent allocations; refinement makes no satisfaction implication or automatic parent-coverage claim."; }
    }

    requirement def <'N-128'> WeedSnagSpeedRecovery {
        metadata workStatus : ModelingMetadata::StatusInfo { status = ModelingMetadata::StatusKind::open; }
        doc /* Within 5 minutes of each N-054 snag, water-relative sailing speed shall recover to at least 50 percent of unobstructed reference speed. */
        comment conditions /*
         *  Apply the N-054 qualification conditions for this criterion. Explicit mode coverage and independent shared obligations stated in N-128 continue to govern. */
    }
    requirement weedSnagSpeedRecovery : WeedSnagSpeedRecovery;

    #derivation connection decomposeWeedSnagSpeedRecovery {
        metadata workStatus : ModelingMetadata::StatusInfo { status = ModelingMetadata::StatusKind::open; }
        metadata rationale : ModelingMetadata::Rationale { text = "This leaf isolates one acceptance outcome of N-054; the parent supplies shared verification conditions."; }
        end #original source ::> weedSnagShedding;
        end #derive target ::> weedSnagSpeedRecovery;
    }

    requirement def <'N-129'> WeedSnagSteeringRecovery {
        metadata workStatus : ModelingMetadata::StatusInfo { status = ModelingMetadata::StatusKind::open; }
        doc /* Within 5 minutes of each N-054 snag, full commanded rudder travel shall be regained. */
        comment conditions /*
         *  Apply the N-054 qualification conditions for this criterion. Explicit mode coverage and independent shared obligations stated in N-129 continue to govern. */
    }
    requirement weedSnagSteeringRecovery : WeedSnagSteeringRecovery;

    #derivation connection decomposeWeedSnagSteeringRecovery {
        metadata workStatus : ModelingMetadata::StatusInfo { status = ModelingMetadata::StatusKind::open; }
        metadata rationale : ModelingMetadata::Rationale { text = "This leaf isolates one acceptance outcome of N-054; the parent supplies shared verification conditions."; }
        end #original source ::> weedSnagShedding;
        end #derive target ::> weedSnagSteeringRecovery;
    }

    requirement def <'N-130'> WeedBlockageFault {
        metadata workStatus : ModelingMetadata::StatusInfo { status = ModelingMetadata::StatusKind::open; }
        doc /* A suspected-fouling fault shall be logged within 10 seconds after the N-055 trigger. */
        comment conditions /*
         *  Apply the N-055 qualification conditions for this criterion. Explicit mode coverage and independent shared obligations stated in N-130 continue to govern. */
    }
    requirement weedBlockageFault : WeedBlockageFault;
    #refinement dependency decomposeWeedBlockageFault from BlueDogRequirements::weedBlockageFault to BlueDogRequirements::weedBlockageResponse {
        metadata workStatus : ModelingMetadata::StatusInfo { status = ModelingMetadata::StatusKind::open; }
        metadata rationale : ModelingMetadata::Rationale { text = "N-130 specifies a detailed acceptance condition for N-055 within their stated applicability. Selected limits, mechanisms and campaign conditions remain independent allocations; refinement makes no satisfaction implication or automatic parent-coverage claim."; }
    }

    requirement def <'N-131'> WeedBlockageContingency {
        metadata workStatus : ModelingMetadata::StatusInfo { status = ModelingMetadata::StatusKind::open; }
        doc /* The vessel shall enter fouling-contingency state within 10 seconds after the N-055 trigger. */
        comment conditions /*
         *  Apply the N-055 qualification conditions for this criterion. Explicit mode coverage and independent shared obligations stated in N-131 continue to govern. */
    }
    requirement weedBlockageContingency : WeedBlockageContingency;
    #refinement dependency decomposeWeedBlockageContingency from BlueDogRequirements::weedBlockageContingency to BlueDogRequirements::weedBlockageResponse {
        metadata workStatus : ModelingMetadata::StatusInfo { status = ModelingMetadata::StatusKind::open; }
        metadata rationale : ModelingMetadata::Rationale { text = "N-131 specifies a detailed acceptance condition for N-055 within their stated applicability. Selected limits, mechanisms and campaign conditions remain independent allocations; refinement makes no satisfaction implication or automatic parent-coverage claim."; }
    }

    requirement def <'N-132'> WeedBlockageLocation {
        metadata workStatus : ModelingMetadata::StatusInfo { status = ModelingMetadata::StatusKind::open; }
        doc /* Location reporting shall continue at the active telemetry cadence during fouling contingency whenever a link is available. */
        comment conditions /*
         *  Apply the N-055 qualification conditions for this criterion. Explicit mode coverage and independent shared obligations stated in N-132 continue to govern. */
    }
    requirement weedBlockageLocation : WeedBlockageLocation;
    #refinement dependency decomposeWeedBlockageLocation from BlueDogRequirements::weedBlockageLocation to BlueDogRequirements::weedBlockageResponse {
        metadata workStatus : ModelingMetadata::StatusInfo { status = ModelingMetadata::StatusKind::open; }
        metadata rationale : ModelingMetadata::Rationale { text = "N-132 specifies a detailed acceptance condition for N-055 within their stated applicability. Selected limits, mechanisms and campaign conditions remain independent allocations; refinement makes no satisfaction implication or automatic parent-coverage claim."; }
    }

    requirement def <'N-133'> PoweredWeedSpeed {
        metadata workStatus : ModelingMetadata::StatusInfo { status = ModelingMetadata::StatusKind::open; }
        doc /* Mean water-relative powered speed through each N-056 patch passage shall be at least 50 percent of weed-free reference speed. */
        comment conditions /*
         *  Apply the N-056 qualification conditions for this criterion. Explicit mode coverage and independent shared obligations stated in N-133 continue to govern. */
    }
    requirement poweredWeedSpeed : PoweredWeedSpeed;
    #refinement dependency decomposePoweredWeedSpeed from BlueDogRequirements::poweredWeedSpeed to BlueDogRequirements::recoveryPropulsorWeeds {
        metadata workStatus : ModelingMetadata::StatusInfo { status = ModelingMetadata::StatusKind::open; }
        metadata rationale : ModelingMetadata::Rationale { text = "N-133 specifies a detailed acceptance condition for N-056 within their stated applicability. Selected limits, mechanisms and campaign conditions remain independent allocations; refinement makes no satisfaction implication or automatic parent-coverage claim."; }
    }

    requirement def <'N-134'> PoweredWeedCurrent {
        metadata workStatus : ModelingMetadata::StatusInfo { status = ModelingMetadata::StatusKind::open; }
        doc /* Motor and controller currents shall remain within their respective rated limits during each N-056 patch passage. */
        comment conditions /*
         *  Apply the N-056 qualification conditions for this criterion. Explicit mode coverage and independent shared obligations stated in N-134 continue to govern. */
    }
    requirement poweredWeedCurrent : PoweredWeedCurrent;

    #derivation connection decomposePoweredWeedCurrent {
        metadata workStatus : ModelingMetadata::StatusInfo { status = ModelingMetadata::StatusKind::open; }
        metadata rationale : ModelingMetadata::Rationale { text = "This leaf isolates one acceptance outcome of N-056; the parent supplies shared verification conditions."; }
        end #original source ::> recoveryPropulsorWeeds;
        end #derive target ::> poweredWeedCurrent;
    }

    requirement def <'N-135'> PoweredWeedTemperature {
        metadata workStatus : ModelingMetadata::StatusInfo { status = ModelingMetadata::StatusKind::open; }
        doc /* Motor and controller temperatures shall remain within their respective rated limits during each N-056 patch passage. */
        comment conditions /*
         *  Apply the N-056 qualification conditions for this criterion. Explicit mode coverage and independent shared obligations stated in N-135 continue to govern. */
    }
    requirement poweredWeedTemperature : PoweredWeedTemperature;

    #derivation connection decomposePoweredWeedTemperature {
        metadata workStatus : ModelingMetadata::StatusInfo { status = ModelingMetadata::StatusKind::open; }
        metadata rationale : ModelingMetadata::Rationale { text = "This leaf isolates one acceptance outcome of N-056; the parent supplies shared verification conditions."; }
        end #original source ::> recoveryPropulsorWeeds;
        end #derive target ::> poweredWeedTemperature;
    }

    requirement def <'N-136'> LockedPropulsorShutdown {
        metadata workStatus : ModelingMetadata::StatusInfo { status = ModelingMetadata::StatusKind::open; }
        doc /* A locked propulsor shall cause motor shutdown within 2 seconds. */
        comment conditions /*
         *  Apply the N-056 qualification conditions for this criterion. Explicit mode coverage and independent shared obligations stated in N-136 continue to govern. */
    }
    requirement lockedPropulsorShutdown : LockedPropulsorShutdown;
    #refinement dependency decomposeLockedPropulsorShutdown from BlueDogRequirements::lockedPropulsorShutdown to BlueDogRequirements::recoveryPropulsorWeeds {
        metadata workStatus : ModelingMetadata::StatusInfo { status = ModelingMetadata::StatusKind::open; }
        metadata rationale : ModelingMetadata::Rationale { text = "N-136 specifies a detailed acceptance condition for N-056 within their stated applicability. Selected limits, mechanisms and campaign conditions remain independent allocations; refinement makes no satisfaction implication or automatic parent-coverage claim."; }
    }

    requirement def <'R-101'> MotorQualificationInvariant {
        metadata workStatus : ModelingMetadata::StatusInfo { status = ModelingMetadata::StatusKind::open; }
        doc /* Motor thrust shall remain disabled whenever an attempt is qualifying or qualification status is unknown. */
        attribute qualifying : Boolean;
        attribute qualificationStateKnown : Boolean;
        attribute motorEnabled : Boolean;
        require constraint motorQualificationInvariant {
            not motorEnabled or (qualificationStateKnown and not qualifying)
        }
        comment conditions /*
         *  Apply the R-004 qualification conditions for this criterion. Explicit mode coverage and independent shared obligations stated in R-101 continue to govern. */
    }
    requirement motorQualificationInvariant : MotorQualificationInvariant;
    #refinement dependency decomposeMotorQualificationInvariant from BlueDogRequirements::motorQualificationInvariant to BlueDogRequirements::challengeMotorInhibition {
        metadata workStatus : ModelingMetadata::StatusInfo { status = ModelingMetadata::StatusKind::open; }
        metadata rationale : ModelingMetadata::Rationale { text = "R-101 specifies a detailed acceptance condition for R-004 within their stated applicability. Selected limits, mechanisms and campaign conditions remain independent allocations; refinement makes no satisfaction implication or automatic parent-coverage claim."; }
    }

    requirement def <'R-102'> FreshRecoveryCommand {
        metadata workStatus : ModelingMetadata::StatusInfo { status = ModelingMetadata::StatusKind::open; }
        doc /* After restart, motor enable shall remain inhibited until recovery is authorized by the onboard safety function or a fresh authenticated operator command. */
        comment conditions /*
         *  Apply the R-004 qualification conditions for this criterion. Explicit mode coverage and independent shared obligations stated in R-102 continue to govern. */
    }
    requirement freshRecoveryCommand : FreshRecoveryCommand;
    #refinement dependency decomposeFreshRecoveryCommand from BlueDogRequirements::freshRecoveryCommand to BlueDogRequirements::challengeMotorInhibition {
        metadata workStatus : ModelingMetadata::StatusInfo { status = ModelingMetadata::StatusKind::open; }
        metadata rationale : ModelingMetadata::Rationale { text = "R-102 specifies a detailed acceptance condition for R-004 within their stated applicability. Selected limits, mechanisms and campaign conditions remain independent allocations; refinement makes no satisfaction implication or automatic parent-coverage claim."; }
    }

    requirement def <'E-144'> IngressEventDeadline {
        metadata workStatus : ModelingMetadata::StatusInfo { status = ModelingMetadata::StatusKind::open; }
        doc /* In the E-006 injection test, an ingress event record shall exist within 60 seconds of injection starting. */
        comment conditions /*
         *  Apply the E-006 qualification conditions for this criterion. Explicit mode coverage and independent shared obligations stated in E-144 continue to govern. */
    }
    requirement ingressEventDeadline : IngressEventDeadline;
    #refinement dependency decomposeIngressEventDeadline from BlueDogRequirements::ingressEventDeadline to BlueDogRequirements::ingressResponse {
        metadata workStatus : ModelingMetadata::StatusInfo { status = ModelingMetadata::StatusKind::open; }
        metadata rationale : ModelingMetadata::Rationale { text = "E-144 specifies a detailed acceptance condition for E-006 within their stated applicability. Selected limits, mechanisms and campaign conditions remain independent allocations; refinement makes no satisfaction implication or automatic parent-coverage claim."; }
    }

    requirement def <'E-145'> QualificationRestoration {
        metadata workStatus : ModelingMetadata::StatusInfo { status = ModelingMetadata::StatusKind::open; }
        doc /* Within 30 seconds after a watchdog reset under E-003 preconditions, qualification status shall equal the valid persisted status, or be nonqualifying when persisted status is absent or inconsistent. */
        comment conditions /*
         *  Apply the E-003 qualification conditions for this criterion. Explicit mode coverage and independent shared obligations stated in E-145 continue to govern. */
    }
    requirement qualificationRestoration : QualificationRestoration;
    #refinement dependency decomposeQualificationRestoration from BlueDogRequirements::qualificationRestoration to BlueDogRequirements::resetRecovery {
        metadata workStatus : ModelingMetadata::StatusInfo { status = ModelingMetadata::StatusKind::open; }
        metadata rationale : ModelingMetadata::Rationale { text = "E-145 specifies a detailed acceptance condition for E-003 within their stated applicability. Selected limits, mechanisms and campaign conditions remain independent allocations; refinement makes no satisfaction implication or automatic parent-coverage claim."; }
    }
    dependency sharedAcceptance1 from BlueDogRequirements::resetRecovery to BlueDogRequirements::logInterruptionDurability {
        metadata workStatus : ModelingMetadata::StatusInfo { status = ModelingMetadata::StatusKind::open; }
        metadata rationale : ModelingMetadata::Rationale { text = "E-003 relies on the E-136 rule only for events and modes within its own qualification context. The full shared rule remains independently applicable and directly verified; this dependency does not derive its other contexts."; }
    }
    dependency sharedAcceptance2 from BlueDogRequirements::resetRecovery to BlueDogRequirements::unknownQualificationFallback {
        metadata workStatus : ModelingMetadata::StatusInfo { status = ModelingMetadata::StatusKind::open; }
        metadata rationale : ModelingMetadata::Rationale { text = "E-003 relies on the E-139 rule only for events and modes within its own qualification context. The full shared rule remains independently applicable and directly verified; this dependency does not derive its other contexts."; }
    }
    dependency sharedAcceptance3 from BlueDogRequirements::resetRecovery to BlueDogRequirements::qualificationPersistence {
        metadata workStatus : ModelingMetadata::StatusInfo { status = ModelingMetadata::StatusKind::open; }
        metadata rationale : ModelingMetadata::Rationale { text = "E-003 relies on the E-138 rule only for events and modes within its own qualification context. The full shared rule remains independently applicable and directly verified; this dependency does not derive its other contexts."; }
    }
    dependency sharedAcceptance4 from BlueDogRequirements::resetRecovery to BlueDogRequirements::freshRecoveryCommand {
        metadata workStatus : ModelingMetadata::StatusInfo { status = ModelingMetadata::StatusKind::open; }
        metadata rationale : ModelingMetadata::Rationale { text = "E-003 relies on the R-102 rule only for events and modes within its own qualification context. The full shared rule remains independently applicable and directly verified; this dependency does not derive its other contexts."; }
    }
    dependency sharedAcceptance5 from BlueDogRequirements::resetRecovery to BlueDogRequirements::motorQualificationInvariant {
        metadata workStatus : ModelingMetadata::StatusInfo { status = ModelingMetadata::StatusKind::open; }
        metadata rationale : ModelingMetadata::Rationale { text = "E-003 relies on the R-101 rule only for events and modes within its own qualification context. The full shared rule remains independently applicable and directly verified; this dependency does not derive its other contexts."; }
    }
    dependency sharedAcceptance6 from BlueDogRequirements::commandIntegrity to BlueDogRequirements::criticalEventRecording {
        metadata workStatus : ModelingMetadata::StatusInfo { status = ModelingMetadata::StatusKind::open; }
        metadata rationale : ModelingMetadata::Rationale { text = "C-102 relies on the E-132 rule only for events and modes within its own qualification context. The full shared rule remains independently applicable and directly verified; this dependency does not derive its other contexts."; }
    }
    dependency sharedAcceptance7 from BlueDogRequirements::commandIntegrity to BlueDogRequirements::qualificationPersistence {
        metadata workStatus : ModelingMetadata::StatusInfo { status = ModelingMetadata::StatusKind::open; }
        metadata rationale : ModelingMetadata::Rationale { text = "C-102 relies on the E-138 rule only for events and modes within its own qualification context. The full shared rule remains independently applicable and directly verified; this dependency does not derive its other contexts."; }
    }
    dependency sharedAcceptance8 from BlueDogRequirements::emergencyControl to BlueDogRequirements::qualificationPersistence {
        metadata workStatus : ModelingMetadata::StatusInfo { status = ModelingMetadata::StatusKind::open; }
        metadata rationale : ModelingMetadata::Rationale { text = "S-003 relies on the E-138 rule only for events and modes within its own qualification context. The full shared rule remains independently applicable and directly verified; this dependency does not derive its other contexts."; }
    }
    dependency sharedAcceptance9 from BlueDogRequirements::emergencyControl to BlueDogRequirements::motorQualificationInvariant {
        metadata workStatus : ModelingMetadata::StatusInfo { status = ModelingMetadata::StatusKind::open; }
        metadata rationale : ModelingMetadata::Rationale { text = "S-003 relies on the R-101 rule only for events and modes within its own qualification context. The full shared rule remains independently applicable and directly verified; this dependency does not derive its other contexts."; }
    }
    dependency sharedAcceptance10 from BlueDogRequirements::emergencyControl to BlueDogRequirements::periodicLogCadence {
        metadata workStatus : ModelingMetadata::StatusInfo { status = ModelingMetadata::StatusKind::open; }
        metadata rationale : ModelingMetadata::Rationale { text = "S-003 relies on the E-130 rule only for events and modes within its own qualification context. The full shared rule remains independently applicable and directly verified; this dependency does not derive its other contexts."; }
    }
    dependency sharedAcceptance11 from BlueDogRequirements::challengeMotorInhibition to BlueDogRequirements::qualificationPersistence {
        metadata workStatus : ModelingMetadata::StatusInfo { status = ModelingMetadata::StatusKind::open; }
        metadata rationale : ModelingMetadata::Rationale { text = "R-004 relies on the E-138 rule only for events and modes within its own qualification context. The full shared rule remains independently applicable and directly verified; this dependency does not derive its other contexts."; }
    }
    dependency sharedAcceptance12 from BlueDogRequirements::challengeMotorInhibition to BlueDogRequirements::criticalEventRecording {
        metadata workStatus : ModelingMetadata::StatusInfo { status = ModelingMetadata::StatusKind::open; }
        metadata rationale : ModelingMetadata::Rationale { text = "R-004 relies on the E-132 rule only for events and modes within its own qualification context. The full shared rule remains independently applicable and directly verified; this dependency does not derive its other contexts."; }
    }
    dependency sharedAcceptance13 from BlueDogRequirements::lowEnergyRecovery to BlueDogRequirements::periodicLogCadence {
        metadata workStatus : ModelingMetadata::StatusInfo { status = ModelingMetadata::StatusKind::open; }
        metadata rationale : ModelingMetadata::Rationale { text = "E-004 relies on the E-130 rule only for events and modes within its own qualification context. The full shared rule remains independently applicable and directly verified; this dependency does not derive its other contexts."; }
    }
    dependency sharedAcceptance14 from BlueDogRequirements::lowEnergyRecovery to BlueDogRequirements::telemetryDeliveryCadence {
        metadata workStatus : ModelingMetadata::StatusInfo { status = ModelingMetadata::StatusKind::open; }
        metadata rationale : ModelingMetadata::Rationale { text = "E-004 relies on the E-120 rule only for events and modes within its own qualification context. The full shared rule remains independently applicable and directly verified; this dependency does not derive its other contexts."; }
    }
    dependency sharedAcceptance15 from BlueDogRequirements::lowEnergyRecovery to BlueDogRequirements::criticalEventRecording {
        metadata workStatus : ModelingMetadata::StatusInfo { status = ModelingMetadata::StatusKind::open; }
        metadata rationale : ModelingMetadata::Rationale { text = "E-004 relies on the E-132 rule only for events and modes within its own qualification context. The full shared rule remains independently applicable and directly verified; this dependency does not derive its other contexts."; }
    }
    dependency sharedAcceptance16 from BlueDogRequirements::lowEnergyRecovery to BlueDogRequirements::motorQualificationInvariant {
        metadata workStatus : ModelingMetadata::StatusInfo { status = ModelingMetadata::StatusKind::open; }
        metadata rationale : ModelingMetadata::Rationale { text = "E-004 relies on the R-101 rule only for events and modes within its own qualification context. The full shared rule remains independently applicable and directly verified; this dependency does not derive its other contexts."; }
    }
    dependency sharedAcceptance17 from BlueDogRequirements::ingressResponse to BlueDogRequirements::criticalEventRecording {
        metadata workStatus : ModelingMetadata::StatusInfo { status = ModelingMetadata::StatusKind::open; }
        metadata rationale : ModelingMetadata::Rationale { text = "E-006 relies on the E-132 rule only for events and modes within its own qualification context. The full shared rule remains independently applicable and directly verified; this dependency does not derive its other contexts."; }
    }
    dependency sharedAcceptance18 from BlueDogRequirements::ingressResponse to BlueDogRequirements::motorQualificationInvariant {
        metadata workStatus : ModelingMetadata::StatusInfo { status = ModelingMetadata::StatusKind::open; }
        metadata rationale : ModelingMetadata::Rationale { text = "E-006 relies on the R-101 rule only for events and modes within its own qualification context. The full shared rule remains independently applicable and directly verified; this dependency does not derive its other contexts."; }
    }
    dependency sharedAcceptance19 from BlueDogRequirements::communications to BlueDogRequirements::logRetention {
        metadata workStatus : ModelingMetadata::StatusInfo { status = ModelingMetadata::StatusKind::open; }
        metadata rationale : ModelingMetadata::Rationale { text = "E-005 relies on the E-131 rule only for events and modes within its own qualification context. The full shared rule remains independently applicable and directly verified; this dependency does not derive its other contexts."; }
    }
    dependency sharedAcceptance20 from BlueDogRequirements::communications to BlueDogRequirements::reconnectLogPreservation {
        metadata workStatus : ModelingMetadata::StatusInfo { status = ModelingMetadata::StatusKind::open; }
        metadata rationale : ModelingMetadata::Rationale { text = "E-005 relies on the E-137 rule only for events and modes within its own qualification context. The full shared rule remains independently applicable and directly verified; this dependency does not derive its other contexts."; }
    }
    dependency sharedAcceptance21 from BlueDogRequirements::navigationAvailability to BlueDogRequirements::criticalEventRecording {
        metadata workStatus : ModelingMetadata::StatusInfo { status = ModelingMetadata::StatusKind::open; }
        metadata rationale : ModelingMetadata::Rationale { text = "E-008 relies on the E-132 rule only for events and modes within its own qualification context. The full shared rule remains independently applicable and directly verified; this dependency does not derive its other contexts."; }
    }
    dependency sharedAcceptance22 from BlueDogRequirements::envelopeTransition to BlueDogRequirements::periodicLogCadence {
        metadata workStatus : ModelingMetadata::StatusInfo { status = ModelingMetadata::StatusKind::open; }
        metadata rationale : ModelingMetadata::Rationale { text = "N-035 relies on the E-130 rule only for events and modes within its own qualification context. The full shared rule remains independently applicable and directly verified; this dependency does not derive its other contexts."; }
    }
    dependency sharedAcceptance23 from BlueDogRequirements::envelopeTransition to BlueDogRequirements::motorQualificationInvariant {
        metadata workStatus : ModelingMetadata::StatusInfo { status = ModelingMetadata::StatusKind::open; }
        metadata rationale : ModelingMetadata::Rationale { text = "N-035 relies on the R-101 rule only for events and modes within its own qualification context. The full shared rule remains independently applicable and directly verified; this dependency does not derive its other contexts."; }
    }
    dependency sharedAcceptance24 from BlueDogRequirements::weedBlockageResponse to BlueDogRequirements::motorQualificationInvariant {
        metadata workStatus : ModelingMetadata::StatusInfo { status = ModelingMetadata::StatusKind::open; }
        metadata rationale : ModelingMetadata::Rationale { text = "N-055 relies on the R-101 rule only for events and modes within its own qualification context. The full shared rule remains independently applicable and directly verified; this dependency does not derive its other contexts."; }
    }
    dependency sharedAcceptance25 from BlueDogRequirements::recoveryPropulsorWeeds to BlueDogRequirements::motorQualificationInvariant {
        metadata workStatus : ModelingMetadata::StatusInfo { status = ModelingMetadata::StatusKind::open; }
        metadata rationale : ModelingMetadata::Rationale { text = "N-056 relies on the R-101 rule only for events and modes within its own qualification context. The full shared rule remains independently applicable and directly verified; this dependency does not derive its other contexts."; }
    }

    requirement def <'E-200'> SustainedEnergyFeasibility {
        metadata applicability : BlueDogMissionScope::Applicability { mission = BlueDogMissionScope::MissionKind::futureEndurance; }
        metadata workStatus : ModelingMetadata::StatusInfo { status = ModelingMetadata::StatusKind::open; }
        doc /* The installed energy architecture shall support the selected bounded repeating profile without external charging, meeting the derived reserve, cycle-balance and peak-supply criteria. */
        comment notes /* A 72-hour energy demonstration does not prove indefinite weather availability, functional performance or ocean readiness. */
    }
    requirement sustainedEnergyFeasibility : SustainedEnergyFeasibility;

    requirement def <'E-201'> SustainedReserveProtection {
        metadata workStatus : ModelingMetadata::StatusInfo { status = ModelingMetadata::StatusKind::open; }
        doc /* Conservative stored energy shall remain strictly above the R-002 protected reserve throughout the selected mission-energy profile. */
        comment conditions /* Apply to the complete finite M-002 history or the future E-200 repeating profile as selected. Route-dependent reserve remains subject to R-002; a fixed reserve input is a declared analysis approximation. */
        comment notes /* Unmodeled intrainterval dips are outside the analysis claim. */
        attribute samples : EnergyValue [1..*] ordered nonunique;
        attribute reserve : EnergyValue;
        attribute verdict : Boolean = SustainedReserveProtectionCriterion(samples, reserve);
        require constraint { verdict }
    }
    requirement sustainedReserveProtection : SustainedReserveProtection;

    requirement def <'E-202'> RepeatableCycleBalance {
        metadata applicability : BlueDogMissionScope::Applicability { mission = BlueDogMissionScope::MissionKind::futureEndurance; }
        metadata workStatus : ModelingMetadata::StatusInfo { status = ModelingMetadata::StatusKind::open; }
        doc /* Stored energy at the end of the complete repeating profile shall be at least its initial value at the same profile phase. */
        comment conditions /* The repeatability criterion assumes fixed capacity, loads and resource bounds. */
        comment notes /* This conditional result is not an indefinite-endurance verdict. */
        attribute initialEnergy : EnergyValue;
        attribute finalEnergy : EnergyValue;
        attribute verdict : Boolean = RepeatableCycleBalanceCriterion(initialEnergy, finalEnergy);
        require constraint { verdict }
    }
    requirement repeatableCycleBalance : RepeatableCycleBalance;

    requirement def <'E-203'> PeakSupplyCapability {
        metadata workStatus : ModelingMetadata::StatusInfo { status = ModelingMetadata::StatusKind::open; }
        doc /* The battery supply shall support each selected mode’s coincident peak withdrawal power without harvesting. */
        comment conditions /* Load power includes conversion losses and the declared uncertainty allowance. */
        attribute demands : PowerValue [1..*] ordered nonunique;
        attribute availablePower : PowerValue;
        attribute verdict : Boolean = PeakSupplyCapabilityCriterion(demands, availablePower);
        require constraint { verdict }
    }
    requirement peakSupplyCapability : PeakSupplyCapability;

    requirement def <'E-204'> HarvestCampaignCoverage {
        metadata applicability : BlueDogMissionScope::Applicability { mission = BlueDogMissionScope::MissionKind::futureEndurance; }
        metadata workStatus : ModelingMetadata::StatusInfo { status = ModelingMetadata::StatusKind::open; }
        doc /* The qualification energy profile shall contain at least three consecutive 24-hour days, each with harvesting enabled for no more than 6 hours. */
        comment conditions /* Each modeled day is gap-free; the remaining time has harvesting disabled. Enabling harvesting with zero resource still counts as enabled. */
        attribute duration : TimeValue;
        attribute dayCount : Integer;
        attribute enabledHours : Real [1..*] ordered nonunique;
        attribute verdict : Boolean = HarvestCampaignCoverageCriterion(duration, dayCount, enabledHours);
        require constraint { verdict }
    }
    requirement harvestCampaignCoverage : HarvestCampaignCoverage;

    requirement def <'E-205'> EnergyEvidenceReadiness {
        metadata workStatus : ModelingMetadata::StatusInfo { status = ModelingMetadata::StatusKind::open; }
        doc /*
         *  The energy-case acceptance record shall identify accepted evidence for installed-load coverage, resource bounds, battery derating and interval resolution before the case is accepted. */
        attribute accepted : Boolean;
        attribute verdict : Boolean = EnergyEvidenceReadinessCriterion(accepted);
        require constraint { verdict }
    }
    requirement energyEvidenceReadiness : EnergyEvidenceReadiness;

    dependency energyDerivation1 from sustainedEnergyFeasibility to GorgeChallenge::repeatedOperation {
        metadata rationale : ModelingMetadata::Rationale { text = "Repeated journeys motivate a repeatable energy cycle, beyond a one-off endurance run. This is design motivation or an implementation choice, not a satisfaction implication."; }
    }

    dependency energyDerivation2 from sustainedEnergyFeasibility to BlueDog::Goals::hawaiiVoyage {
        metadata rationale : ModelingMetadata::Rationale { text = "The ocean ambition requires sustained energy autonomy; route-specific resources remain unresolved. This is design motivation or an implementation choice, not a satisfaction implication."; }
    }

    #derivation connection energyDerivation3 {
        metadata workStatus : ModelingMetadata::StatusInfo { status = ModelingMetadata::StatusKind::open; }
        metadata rationale : ModelingMetadata::Rationale { text = "This leaf isolates one acceptance outcome of sustained energy feasibility."; }
        end #original source ::> sustainedEnergyFeasibility;
        end #derive target ::> sustainedReserveProtection;
    }

    #derivation connection energyDerivation4 {
        metadata workStatus : ModelingMetadata::StatusInfo { status = ModelingMetadata::StatusKind::open; }
        metadata rationale : ModelingMetadata::Rationale { text = "This leaf isolates one acceptance outcome of sustained energy feasibility."; }
        end #original source ::> sustainedEnergyFeasibility;
        end #derive target ::> repeatableCycleBalance;
    }

    #derivation connection energyDerivation5 {
        metadata workStatus : ModelingMetadata::StatusInfo { status = ModelingMetadata::StatusKind::open; }
        metadata rationale : ModelingMetadata::Rationale { text = "This leaf isolates one acceptance outcome of sustained energy feasibility."; }
        end #original source ::> sustainedEnergyFeasibility;
        end #derive target ::> peakSupplyCapability;
    }
    dependency energyDerivation6 from BlueDogRequirements::energyEvidenceReadiness to BlueDogRequirements::sustainedEnergyFeasibility {
        metadata workStatus : ModelingMetadata::StatusInfo { status = ModelingMetadata::StatusKind::open; }
        metadata rationale : ModelingMetadata::Rationale { text = "E-205 is an evidence-acceptance work product supporting E-200; a product capability does not logically entail the assurance record."; }
    }

    #derivation connection energyDerivation7 {
        metadata workStatus : ModelingMetadata::StatusInfo { status = ModelingMetadata::StatusKind::open; }
        metadata rationale : ModelingMetadata::Rationale { text = "The M-002 campaign requires this separately evaluated energy outcome."; }
        end #original source ::> multiDayEndurance;
        end #derive target ::> sustainedReserveProtection;
    }
    #refinement dependency energyDerivation8 from BlueDogRequirements::peakSupplyCapability to BlueDogRequirements::multiDayEndurance {
        metadata workStatus : ModelingMetadata::StatusInfo { status = ModelingMetadata::StatusKind::open; }
        metadata rationale : ModelingMetadata::Rationale { text = "E-203 specifies a detailed acceptance condition for M-002 within their stated applicability. Selected limits, mechanisms and campaign conditions remain independent allocations; refinement makes no satisfaction implication or automatic parent-coverage claim."; }
    }
    #refinement dependency energyDerivation9 from BlueDogRequirements::harvestCampaignCoverage to BlueDogRequirements::sustainedEnergyFeasibility {
        metadata workStatus : ModelingMetadata::StatusInfo { status = ModelingMetadata::StatusKind::open; }
        metadata rationale : ModelingMetadata::Rationale { text = "E-204 specifies a detailed acceptance condition for E-200 within their stated applicability. Selected limits, mechanisms and campaign conditions remain independent allocations; refinement makes no satisfaction implication or automatic parent-coverage claim."; }
    }
    dependency energyDerivation10 from BlueDogRequirements::energyEvidenceReadiness to BlueDogRequirements::multiDayEndurance {
        metadata workStatus : ModelingMetadata::StatusInfo { status = ModelingMetadata::StatusKind::open; }
        metadata rationale : ModelingMetadata::Rationale { text = "E-205 is an evidence-acceptance work product supporting M-002; a product capability does not logically entail the assurance record."; }
    }

    dependency energyDerivation11 from sustainedReserveProtection to recoveryEnergy {
        metadata rationale : ModelingMetadata::Rationale { text = "Sustained operation protects the recovery reserve sized by the existing R-002 policy. This is design motivation or an implementation choice, not a satisfaction implication."; }
    }

    calc def SustainedReserveProtectionCriterion {
        in samples : EnergyValue [1..*] ordered nonunique;
        in reserve : EnergyValue;
        return verdict : Boolean;
        reserve > 0 [J] and SequenceFunctions::size(samples) > 0 and
        samples->ControlFunctions::forAll { in e : EnergyValue; e > reserve }
    }

    calc def RepeatableCycleBalanceCriterion {
        in initialEnergy : EnergyValue;
        in finalEnergy : EnergyValue;
        return verdict : Boolean;
        initialEnergy > 0 [J] and finalEnergy >= initialEnergy
    }

    calc def PeakSupplyCapabilityCriterion {
        in demands : PowerValue [1..*] ordered nonunique;
        in availablePower : PowerValue;
        return verdict : Boolean;
        availablePower > 0 [W] and SequenceFunctions::size(demands) > 0 and
        demands->ControlFunctions::forAll { in p : PowerValue; p >= 0 [W] and p <= availablePower }
    }

    calc def HarvestCampaignCoverageCriterion {
        in duration : TimeValue;
        in dayCount : Integer;
        in enabledHours : Real [1..*] ordered nonunique;
        return verdict : Boolean;
        dayCount >= 3 and duration == dayCount * 86400 [s] and
        SequenceFunctions::size(enabledHours) == dayCount and
        enabledHours->ControlFunctions::forAll { in hours : Real; hours >= 0 and hours <= 6 }
    }

    calc def EnergyEvidenceReadinessCriterion {
        in accepted : Boolean;
        return verdict : Boolean;
        accepted
    }
    requirement def <'Q-001'> CruisePerformance {
        metadata workStatus : ModelingMetadata::StatusInfo { status = ModelingMetadata::StatusKind::open; }
        doc /* The vessel shall sustain sailing performance sufficient to complete each declared unassisted mission route. */
        comment conditions /* The declared route includes sailing legs, current projections, weather holds and maneuvering time. The Gorge qualifying attempt uses a selected weather window, with westerly flow as the representative sizing case. Winter testing and eventual year-round operation use separate declared profiles. Apply Q-101 through Q-103; see BlueDogWeather::policy. */
        metadata rationale : ModelingMetadata::Rationale { text = "Cruise speed determines exposure to failures; water speed alone does not establish route completion."; }
    }
    requirement cruisePerformance : CruisePerformance;
    requirement def <'Q-101'> LegProgress {
        metadata workStatus : ModelingMetadata::StatusInfo { status = ModelingMetadata::StatusKind::open; }
        doc /*
         *  The mission-performance assessment shall evaluate complete-route progress over the declared reproducible scenario ensemble, including sailing legs, holds and maneuvers. */
        comment conditions /* Evaluate sailing-only, loaded configuration under the declared wind, wave, current and fouling profile. Include tacking in water-relative velocity made good. Holds are separate exposure intervals, not discarded samples. */
        metadata rationale : ModelingMetadata::Rationale { text = "Owner decision: no fixed minimum sailing speed. Compare complete passage, waiting, aborts, recovery reserve and model coverage using the same versioned scenario set across designs."; }
        metadata issue : ModelingMetadata::Issue { text = "Proposed target pending design review and mission-profile selection."; }
        attribute groundSpeeds : SpeedValue [1..*] ordered nonunique;
        comment assessment /* Ground speeds are analysis outputs, not a fixed-speed acceptance predicate. Mission outcomes govern the performance trade. */
    }
    requirement legProgress : LegProgress;
    requirement def <'Q-102'> PassageDuration {
        metadata workStatus : ModelingMetadata::StatusInfo { status = ModelingMetadata::StatusKind::open; }
        doc /* The vessel shall complete the declared route within the qualified unassisted operating duration. */
        comment conditions /* Passage duration includes every sailing leg, weather hold and maneuver. Qualified duration must come from the same configuration and applicable environment. */
        metadata rationale : ModelingMetadata::Rationale { text = "A fast moving-leg average cannot conceal long periods waiting for usable wind."; }
        attribute voyageDuration : TimeValue;
        attribute qualifiedDuration : TimeValue;
        require constraint acceptance { PassageDurationCriterion(voyageDuration, qualifiedDuration) }
    }
    requirement passageDuration : PassageDuration;
    requirement def <'Q-103'> CruiseEvidence {
        metadata workStatus : ModelingMetadata::StatusInfo { status = ModelingMetadata::StatusKind::open; }
        doc /* The cruise-performance assessment shall use accepted loaded-vessel sailing evidence for its declared mission profile. */
        comment conditions /* Evidence records route distance, wind/sea state, signed along-route current, sailing polar or measured velocity made good, fouling allowance, holds, uncertainty and configuration. No auxiliary propulsion credit for the Gorge challenge. */
        metadata rationale : ModelingMetadata::Rationale { text = "Synthetic inputs support sensitivity analysis only."; }
    }
    requirement cruiseEvidence : CruiseEvidence;
    requirement def <'L-001'> MissionReliability {
        metadata workStatus : ModelingMetadata::StatusInfo { status = ModelingMetadata::StatusKind::open; }
        doc /* The vessel shall preserve mission-critical functions throughout each declared unassisted voyage. */
        comment conditions /* L-103 evidence and L-104 failure dispositions apply to the finite Gorge attempt. L-101 and L-102 are provisional study objectives, not launch or mission-acceptance thresholds. Hawaii reliability targets require a separate future allocation. Failure includes loss of required control, mission completion, safety function or required observation service. Recovery that violates the mission rules is not success. */
        metadata rationale : ModelingMetadata::Rationale { text = "Longer passages impose tighter reliability budgets; Gorge performance does not qualify an ocean mission."; }
    }
    requirement missionReliability : MissionReliability;
    requirement def <'L-101'> MissionSuccessProbability {
        metadata workStatus : ModelingMetadata::StatusInfo { status = ModelingMetadata::StatusKind::open; }
        doc /* The reliability study should assess a provisional objective of 0.90 mission reliability at 95-percent confidence over the declared voyage duration. */
        comment conditions /* Reliability means absence of mission-critical failure over total elapsed exposure, including holds. Statistical evidence must represent the declared configuration, environment and failure definition. */
        metadata rationale : ModelingMetadata::Rationale { text = "0.90 at 95-percent confidence is a proposed engineering target. It is not a measured reliability estimate."; }
        metadata issue : ModelingMetadata::Issue { text = "Proposed target pending design review and mission-profile selection."; }
        attribute lowerBound : Real;
        attribute confidence : Real;
        comment assessment /* MissionReliabilityCriterion is available for study comparisons; this provisional objective is not a challenge acceptance constraint. */
    }
    requirement missionSuccessProbability : MissionSuccessProbability;
    requirement def <'L-102'> FailureRateBudget {
        metadata workStatus : ModelingMetadata::StatusInfo { status = ModelingMetadata::StatusKind::open; }
        doc /* The reliability study should compare the combined mission-critical failure-rate bound with the provisional L-101 objective over Q-102 exposure. */
        comment conditions /* The initial constant-hazard model sums non-overlapping independent critical failure rates plus a separately assessed common-cause contribution. Component bounds require a joint-confidence argument; summing individual 95-percent bounds does not establish a system 95-percent bound. Wear, systematic software faults, variable stress and recovery need a different model when this assumption is unsupported. */
        metadata rationale : ModelingMetadata::Rationale { text = "Use lambda_max = -ln(0.90)/T. Do not sum DFMEA ordinal rankings or assume missing rates are zero."; }
        attribute ratePerHour : Real;
        attribute exposureHours : Real;
        comment assessment /* FailureRateCriterion evaluates the provisional study objective; it is not a binding qualification constraint. */
    }
    requirement failureRateBudget : FailureRateBudget;
    requirement def <'L-103'> ReliabilityEvidence {
        metadata workStatus : ModelingMetadata::StatusInfo { status = ModelingMetadata::StatusKind::open; }
        doc /* The reliability assessment shall use accepted mission-representative evidence supporting its failure-rate bound. */
        comment conditions /* Document confidence method, censoring, configuration, mission profile, exposure and observed critical failures. The initial zero-failure demonstration is invalid when failures occurred or the constant-hazard assumption is unsupported. */
        metadata rationale : ModelingMetadata::Rationale { text = "A numerical estimate is not a confidence bound; shorter tests cannot establish an indefinite lifetime."; }
    }
    requirement reliabilityEvidence : ReliabilityEvidence;
    requirement def <'L-104'> CriticalFailureDisposition {
        metadata workStatus : ModelingMetadata::StatusInfo { status = ModelingMetadata::StatusKind::open; }
        doc /* Each identified safety-critical failure mode shall have an accepted disposition before an unassisted launch. */
        comment conditions /* Acceptance requires evidence for prevention, detection and response, or an explicitly reviewed residual risk. The DFMEA starter is incomplete; completing listed rows does not demonstrate hazard coverage. */
        metadata rationale : ModelingMetadata::Rationale { text = "Potential harm to other waterway users must not be traded against an attractive aggregate reliability score."; }
    }
    requirement criticalFailureDisposition : CriticalFailureDisposition;
    dependency cruiseReliabilityDerivation1 from cruisePerformance to roundTrip {
        metadata rationale : ModelingMetadata::Rationale { text = "cruisePerformance is a selected engineering objective supporting roundTrip. This is design motivation or an implementation choice, not a satisfaction implication."; }
    }
    dependency cruiseReliabilityDerivation3 from missionReliability to roundTrip {
        metadata rationale : ModelingMetadata::Rationale { text = "missionReliability is a selected engineering objective supporting roundTrip. This is design motivation or an implementation choice, not a satisfaction implication."; }
    }
    #derivation connection cruiseReliabilityDerivation6 {
        metadata workStatus : ModelingMetadata::StatusInfo { status = ModelingMetadata::StatusKind::open; }
        metadata rationale : ModelingMetadata::Rationale { text = "legProgress supplies an acceptance condition needed to achieve cruisePerformance."; }
        end #original source ::> cruisePerformance;
        end #derive target ::> legProgress;
    }
    #derivation connection cruiseReliabilityDerivation7 {
        metadata workStatus : ModelingMetadata::StatusInfo { status = ModelingMetadata::StatusKind::open; }
        metadata rationale : ModelingMetadata::Rationale { text = "passageDuration supplies an acceptance condition needed to achieve cruisePerformance."; }
        end #original source ::> cruisePerformance;
        end #derive target ::> passageDuration;
    }
    #derivation connection cruiseReliabilityDerivation8 {
        metadata workStatus : ModelingMetadata::StatusInfo { status = ModelingMetadata::StatusKind::open; }
        metadata rationale : ModelingMetadata::Rationale { text = "cruiseEvidence supplies an acceptance condition needed to achieve cruisePerformance."; }
        end #original source ::> cruisePerformance;
        end #derive target ::> cruiseEvidence;
    }
    dependency cruiseReliabilityDerivation9 from missionSuccessProbability to missionReliability {
        metadata rationale : ModelingMetadata::Rationale { text = "The provisional probability/confidence objective supports reliability studies; preserving required functions does not entail this unaccepted numerical target."; }
    }
    dependency cruiseReliabilityDerivation10 from failureRateBudget to missionReliability {
        metadata rationale : ModelingMetadata::Rationale { text = "The constant-hazard budget is one provisional study model. Mission capability does not require this failure distribution or establish its evidence."; }
    }
    #derivation connection cruiseReliabilityDerivation11 {
        metadata workStatus : ModelingMetadata::StatusInfo { status = ModelingMetadata::StatusKind::open; }
        metadata rationale : ModelingMetadata::Rationale { text = "reliabilityEvidence supplies an acceptance condition needed to achieve missionReliability."; }
        end #original source ::> missionReliability;
        end #derive target ::> reliabilityEvidence;
    }
    #derivation connection cruiseReliabilityDerivation12 {
        metadata workStatus : ModelingMetadata::StatusInfo { status = ModelingMetadata::StatusKind::open; }
        metadata rationale : ModelingMetadata::Rationale { text = "criticalFailureDisposition supplies an acceptance condition needed to achieve missionReliability."; }
        end #original source ::> missionReliability;
        end #derive target ::> criticalFailureDisposition;
    }
    calc def LegProgressCriterion {
        in speeds : SpeedValue [1..*] ordered nonunique;
        return verdict : Boolean;
        SequenceFunctions::size(speeds) > 0 and speeds->ControlFunctions::forAll { in speed : SpeedValue; speed >= 0.5 [m/s] }
    }
    calc def PassageDurationCriterion {
        in exposure : TimeValue;
        in qualified : TimeValue;
        return verdict : Boolean;
        exposure > 0 [s] and qualified > 0 [s] and exposure <= qualified
    }
    calc def MissionReliabilityCriterion {
        in lowerBound : Real;
        in confidence : Real;
        return verdict : Boolean;
        lowerBound >= 0.90 and lowerBound <= 1 and confidence >= 0.95 and confidence < 1
    }
    calc def FailureRateCriterion {
        in ratePerHour : Real;
        in exposureHours : Real;
        return verdict : Boolean;
        ratePerHour >= 0 and exposureHours > 0 and ratePerHour * exposureHours <= -OpenSysMLMathFunctions::ln(0.90)
    }

    // Refine numerical acceptance; these links do not establish physical evidence.
    #refinement dependency formalizeSustainedReserveProtectionCriterion from SustainedReserveProtectionCriterion to sustainedReserveProtection {
        metadata rationale : ModelingMetadata::Rationale { text = "Formalizes the numerical acceptance relation on supplied inputs. The requirement qualification conditions, input representativeness and evidence obligations still apply."; }
    }
    #refinement dependency formalizeRepeatableCycleBalanceCriterion from RepeatableCycleBalanceCriterion to repeatableCycleBalance {
        metadata rationale : ModelingMetadata::Rationale { text = "Formalizes the numerical acceptance relation on supplied inputs. The requirement qualification conditions, input representativeness and evidence obligations still apply."; }
    }
    #refinement dependency formalizePeakSupplyCapabilityCriterion from PeakSupplyCapabilityCriterion to peakSupplyCapability {
        metadata rationale : ModelingMetadata::Rationale { text = "Formalizes the numerical acceptance relation on supplied inputs. The requirement qualification conditions, input representativeness and evidence obligations still apply."; }
    }
    #refinement dependency formalizeHarvestCampaignCoverageCriterion from HarvestCampaignCoverageCriterion to harvestCampaignCoverage {
        metadata rationale : ModelingMetadata::Rationale { text = "Formalizes the numerical acceptance relation on supplied inputs. The requirement qualification conditions, input representativeness and evidence obligations still apply."; }
    }
    dependency studyLegProgressCriterion from LegProgressCriterion to legProgress {
        metadata rationale : ModelingMetadata::Rationale { text = "Legacy or provisional numerical study screen, retained for comparison with recorded analyses. This is not a current challenge acceptance refinement."; }
    }
    #refinement dependency formalizePassageDurationCriterion from PassageDurationCriterion to passageDuration {
        metadata rationale : ModelingMetadata::Rationale { text = "Formalizes the numerical acceptance relation on supplied inputs. The requirement qualification conditions, input representativeness and evidence obligations still apply."; }
    }
    dependency studyMissionReliabilityCriterion from MissionReliabilityCriterion to missionSuccessProbability {
        metadata rationale : ModelingMetadata::Rationale { text = "Legacy or provisional numerical study screen, retained for comparison with recorded analyses. This is not a current challenge acceptance refinement."; }
    }
    dependency studyFailureRateCriterion from FailureRateCriterion to failureRateBudget {
        metadata rationale : ModelingMetadata::Rationale { text = "Legacy or provisional numerical study screen, retained for comparison with recorded analyses. This is not a current challenge acceptance refinement."; }
    }
    private import RequirementDerivation::*;
    requirement def <'E-009'> WindObservation {
        metadata workStatus : ModelingMetadata::StatusInfo { status = ModelingMetadata::StatusKind::open; }
        doc /* The vessel shall provide onboard apparent-wind observations for autonomous sail control. */
        comment conditions /* Qualify the complete installation, including sensor, alignment, vessel-frame transformation and communication interface. Use a calibrated wind reference at the sensor location, speeds 2, 5, 10, 15 and 20 m/s, headings every 30 degrees, heels -20, 0 and 20 degrees, and all intended rig trim positions. Evaluate each 30-minute steady test independently; every scheduled one-second observation must satisfy the applicable criterion. Fault tests inject link loss, frozen timestamps, malformed data and power interruption separately. */
        metadata rationale : ModelingMetadata::Rationale { text = "Sail trim depends on apparent-wind direction and loading depends on speed. Closed-loop autonomous sailing needs onboard observations independent of shore telemetry. One-second updates align with sail-command cadence; 5 degrees and max(0.5 m/s,5 percent) are initial installed-error allocations to refine with control sensitivity analysis."; }
        metadata issue : ModelingMetadata::Issue { text = "Validate sensor exposure, mast/wing interference, heel transformation and degraded trim behavior. Local apparent wind is distinct from the 10 m true-wind environmental reference; envelope detection needs a separate estimation model. Extend accuracy qualification beyond 20 m/s if survival control depends on precise wind measurements."; }
    }
    requirement windObservation : WindObservation;
    dependency windForAutonomousControl from windObservation to navigationAndControl {
        metadata rationale : ModelingMetadata::Rationale { text = "Apparent-wind feedback is the selected implementation for autonomous sail trim. This is a design-basis dependency, not an assertion that every autonomous sailing architecture must use this sensor."; }
    }
    dependency windForSailOnlyMission from windObservation to GorgeChallenge::sailingPropulsion {
        metadata rationale : ModelingMetadata::Rationale { text = "Changes to the sail-only operating concept require review of the selected wind-feedback strategy; sailing propulsion alone does not prescribe a sensor technology."; }
    }
    dependency windEnduranceBasis from windSensingEndurance to multiDayEndurance {
        metadata rationale : ModelingMetadata::Rationale { text = "A change to the finite mission exposure changes installed sensing endurance and energy evidence; the mission does not imply a fixed campaign duration."; }
    }
    requirement def <'E-146'> WindSampleCadence {
        metadata workStatus : ModelingMetadata::StatusInfo { status = ModelingMetadata::StatusKind::open; }
        doc /* The vessel shall deliver apparent-wind observations to sail control at intervals no greater than 1 second. */
        comment conditions /* E-009 supplies installed measurement and fault-test conditions. */
    }
    requirement windSampleCadence : WindSampleCadence;
    #refinement dependency decomposeWindSampleCadence from BlueDogRequirements::windSampleCadence to BlueDogRequirements::windObservation {
        metadata workStatus : ModelingMetadata::StatusInfo { status = ModelingMetadata::StatusKind::open; }
        metadata rationale : ModelingMetadata::Rationale { text = "E-146 specifies a detailed acceptance condition for E-009 within their stated applicability. Selected limits, mechanisms and campaign conditions remain independent allocations; refinement makes no satisfaction implication or automatic parent-coverage claim."; }
    }
    requirement def <'E-147'> WindSpeedAccuracy {
        metadata workStatus : ModelingMetadata::StatusInfo { status = ModelingMetadata::StatusKind::open; }
        doc /* Installed apparent-wind speed error shall not exceed the greater of 0.5 m/s or 5 percent of reference speed. */
        comment conditions /* E-009 supplies installed measurement and fault-test conditions. */
    }
    requirement windSpeedAccuracy : WindSpeedAccuracy;
    #refinement dependency decomposeWindSpeedAccuracy from BlueDogRequirements::windSpeedAccuracy to BlueDogRequirements::windObservation {
        metadata workStatus : ModelingMetadata::StatusInfo { status = ModelingMetadata::StatusKind::open; }
        metadata rationale : ModelingMetadata::Rationale { text = "E-147 specifies a detailed acceptance condition for E-009 within their stated applicability. Selected limits, mechanisms and campaign conditions remain independent allocations; refinement makes no satisfaction implication or automatic parent-coverage claim."; }
    }
    requirement def <'E-148'> WindDirectionAccuracy {
        metadata workStatus : ModelingMetadata::StatusInfo { status = ModelingMetadata::StatusKind::open; }
        doc /* Installed apparent-wind direction error relative to the vessel heading shall not exceed 5 degrees. */
        comment conditions /* E-009 supplies installed measurement and fault-test conditions. */
    }
    requirement windDirectionAccuracy : WindDirectionAccuracy;
    #refinement dependency decomposeWindDirectionAccuracy from BlueDogRequirements::windDirectionAccuracy to BlueDogRequirements::windObservation {
        metadata workStatus : ModelingMetadata::StatusInfo { status = ModelingMetadata::StatusKind::open; }
        metadata rationale : ModelingMetadata::Rationale { text = "E-148 specifies a detailed acceptance condition for E-009 within their stated applicability. Selected limits, mechanisms and campaign conditions remain independent allocations; refinement makes no satisfaction implication or automatic parent-coverage claim."; }
    }
    requirement def <'E-149'> WindStaleInvalidation {
        metadata workStatus : ModelingMetadata::StatusInfo { status = ModelingMetadata::StatusKind::open; }
        doc /* The vessel shall mark wind observations invalid when their age exceeds 2 seconds. */
        comment conditions /* E-009 supplies installed measurement and fault-test conditions. */
    }
    requirement windStaleInvalidation : WindStaleInvalidation;
    #refinement dependency decomposeWindStaleInvalidation from BlueDogRequirements::windStaleInvalidation to BlueDogRequirements::windObservation {
        metadata workStatus : ModelingMetadata::StatusInfo { status = ModelingMetadata::StatusKind::open; }
        metadata rationale : ModelingMetadata::Rationale { text = "E-149 specifies a detailed acceptance condition for E-009 within their stated applicability. Selected limits, mechanisms and campaign conditions remain independent allocations; refinement makes no satisfaction implication or automatic parent-coverage claim."; }
    }
    requirement def <'E-150'> InvalidWindUseInhibition {
        metadata workStatus : ModelingMetadata::StatusInfo { status = ModelingMetadata::StatusKind::open; }
        doc /* Sail control shall exclude invalid wind observations from trim calculations. */
        comment conditions /* E-009 supplies installed measurement and fault-test conditions. */
    }
    requirement invalidWindUseInhibition : InvalidWindUseInhibition;
    #refinement dependency decomposeInvalidWindUseInhibition from BlueDogRequirements::invalidWindUseInhibition to BlueDogRequirements::windObservation {
        metadata workStatus : ModelingMetadata::StatusInfo { status = ModelingMetadata::StatusKind::open; }
        metadata rationale : ModelingMetadata::Rationale { text = "E-150 specifies a detailed acceptance condition for E-009 within their stated applicability. Selected limits, mechanisms and campaign conditions remain independent allocations; refinement makes no satisfaction implication or automatic parent-coverage claim."; }
    }
    requirement def <'E-151'> WindLossResponse {
        metadata workStatus : ModelingMetadata::StatusInfo { status = ModelingMetadata::StatusKind::open; }
        doc /* The vessel shall enter its wind-sensing-degraded control state within 1 second after wind observations become invalid. */
        comment conditions /* E-009 supplies installed measurement and fault-test conditions. */
    }
    requirement windLossResponse : WindLossResponse;
    #refinement dependency decomposeWindLossResponse from BlueDogRequirements::windLossResponse to BlueDogRequirements::windObservation {
        metadata workStatus : ModelingMetadata::StatusInfo { status = ModelingMetadata::StatusKind::open; }
        metadata rationale : ModelingMetadata::Rationale { text = "E-151 specifies a detailed acceptance condition for E-009 within their stated applicability. Selected limits, mechanisms and campaign conditions remain independent allocations; refinement makes no satisfaction implication or automatic parent-coverage claim."; }
    }
    requirement def <'E-152'> WindSensingEndurance {
        metadata workStatus : ModelingMetadata::StatusInfo { status = ModelingMetadata::StatusKind::open; }
        doc /* The wind-sensing installation shall operate throughout the complete M-002 mission without servicing or external charging. */
        comment conditions /* Use the installed configuration through the complete M-002 energy campaign, including its holds and maneuvers. E-009 separately qualifies installed measurement and fault response. */
    }
    requirement windSensingEndurance : WindSensingEndurance;
    #refinement dependency decomposeWindSensingEndurance from BlueDogRequirements::windSensingEndurance to BlueDogRequirements::windObservation {
        metadata workStatus : ModelingMetadata::StatusInfo { status = ModelingMetadata::StatusKind::open; }
        metadata rationale : ModelingMetadata::Rationale { text = "E-152 specifies a detailed acceptance condition for E-009 within their stated applicability. Selected limits, mechanisms and campaign conditions remain independent allocations; refinement makes no satisfaction implication or automatic parent-coverage claim."; }
    }
    requirement def <'N-004'> VegetationResilience {
        doc /* The vessel shall preserve or autonomously recover the sailing and recovery functions specified for the declared submerged-vegetation encounters. */
        comment conditions /* N-053 through N-056 define distinct passage, snag, blockage and powered-recovery cases under the declared Gorge exposure. Submerged-weed qualification excludes dense floating mats and fishing-line entanglement. No disturbance waives required safety capability or motor inhibition. */
        metadata workStatus : ModelingMetadata::StatusInfo { status = ModelingMetadata::StatusKind::open; }
    }
    requirement vegetationResilience : VegetationResilience;
    dependency vegetationEnvironmentBasis from vegetationResilience to environmentalEnvelope;

    dependency navigationDutyBasis from trafficSafety to GorgeChallenge::navigationRules;
    dependency recoverySignalBasis from navigationConspicuity to GorgeChallenge::recoveryConspicuity;
    dependency signalMatrixBasis from navigationConspicuity to regulatoryClassification;

}

package BlueDogSourceEvidence {
    private import ScalarValues::*;
    part def SourceNote { attribute urls : String [1..*] ordered; attribute researchDate : String = "2026-10-09"; }
    part sail1 : SourceNote {
        doc /* The tail-controlled wing uses aerodynamic control of the main wing's incidence. The actuator moves a small tail control surface rather than directly driving the entire loaded wing. Saildrone describes that wing/tail/tab arrangement in its [design history](https://www.saildrone.com/eu-en/news/how-saildrone-wing-was-born). That supports investigating low trim energy; it does not supply a Blue Dog actuator power value or prove that a jammed actuator will feather safely. */
        attribute :>> urls = ("https://www.saildrone.com/eu-en/news/how-saildrone-wing-was-born");
    }
    dependency sail1Basis from BlueDogDesignDecisions::sizingBaseline to sail1;
    part sail2 : SourceNote {
        doc /* The [Silva et al. wingsail design paper](https://recipp.ipp.pt/bitstream/10400.22/15346/1/CAPL_LSA_MBM_2019.pdf) describes the corresponding moment balance and highlights the tail/counterweight trade: balancing a free wing can add elevated mass and increase its swept envelope. This motivates retaining the tail-controlled candidate, while bearing friction, tail authority, tab faults, submerged loads and counterweight mass must remain explicit design problems. */
        attribute :>> urls = ("https://recipp.ipp.pt/bitstream/10400.22/15346/1/CAPL_LSA_MBM_2019.pdf");
    }
    dependency sail2Basis from BlueDogDesignDecisions::sizingBaseline to sail2;
    part sail3 : SourceNote {
        doc /* The closest primary precedent found is Miller, Judge, Sewell and Williamson's [*An Alternative Wing Sail Concept for Small Autonomous Sailing Craft*](https://www.researchgate.net/publication/323361410_An_Alternative_Wing_Sail_Concept_for_Small_Autonomous_Sailing_Craft), published in *Robotic Sailing 2017* (2018), DOI 10.1007/978-3-319-72739-4_1. Its abstract reports wind-tunnel and on-water evaluation of a square-sail-derived wing on the 1.2 m MaxiMOOP, with condition-dependent performance and practical advantages over its soft-sail comparator. The [MaxiMOOP platform page](https://www.sailbot.org/maximoop/) associates the asymmetric-wing test platform with the U.S. Naval Academy. This is the closest match located, not a confirmed NPS-authored paper. The accessible abstract supports concept precedent; the full numerical results have not been inspected or imported. */
        attribute :>> urls = ("https://www.researchgate.net/publication/323361410_An_Alternative_Wing_Sail_Concept_for_Small_Autonomous_Sailing_Craft", "https://www.sailbot.org/maximoop/");
    }
    dependency sail3Basis from BlueDogDesignDecisions::sizingBaseline to sail3;
    part sail4 : SourceNote {
        doc /* [Crescent-wing research at Chalmers](https://research.chalmers.se/publication/543872/file/543872_Fulltext.pdf) explains how suitable sections exchange leading and trailing edges between tacks. Fixed camber therefore does not inherently require a reversal mechanism. Whether our CAD has the necessary edge geometry remains a geometry check, not an assumed property. */
        attribute :>> urls = ("https://research.chalmers.se/publication/543872/file/543872_Fulltext.pdf");
    }
    dependency sail4Basis from BlueDogDesignDecisions::sizingBaseline to sail4;
    part sail5 : SourceNote {
        doc /* The [official PC13 entry](https://www.microtransat.org/content.php?p=2026_oshen_cstar) describes a single DynaRig wingsail driven by a motor inside the hull, a 1.299 m hull, 56 kg displacement, 52.5 W solar and a 100 Ah battery. Its auxiliary thruster was unused during the challenge. Neither the airfoil section nor the gearbox's backdrivability is established by that description. PC13 strengthens the case for direct mast actuation; it does not verify our fixed-camber geometry or energy budget. */
        attribute :>> urls = ("https://www.microtransat.org/content.php?p=2026_oshen_cstar");
    }
    dependency sail5Basis from BlueDogDesignDecisions::sizingBaseline to sail5;
    part sail6 : SourceNote {
        doc /* The [organizer announced autonomous east-to-west completion on 13 September 2026](https://microtransat.org/content.php?p=news%2F2026-09-13-oshen), with the result provisional pending jury review in that announcement. This is relevant integrated endurance evidence, not a statistical reliability estimate. The [Oshen/MBARI evaluation of other C-Star configurations](https://oceansynchro.io/wp-content/uploads/2026/05/OshenC-Star_ReportFinal-1.pdf) identified light-wind/current navigation limitations and evaluated auxiliary propulsion. An ocean crossing therefore does not establish sail-only upstream Gorge progress. PC13's compact length also does not establish compliance with our one-person handling allocations. */
        attribute :>> urls = ("https://microtransat.org/content.php?p=news%2F2026-09-13-oshen", "https://oceansynchro.io/wp-content/uploads/2026/05/OshenC-Star_ReportFinal-1.pdf");
    }
    dependency sail6Basis from BlueDogDesignDecisions::sizingBaseline to sail6;
    part sail7 : SourceNote {
        doc /* [SEW's gearbox planning guidance](https://download.sew-eurodrive.com/download/pdf/16934016.pdf) distinguishes starting and running efficiency, and static and dynamic self-locking. We must verify the selected unit's holding behavior across load, lubrication, temperature, wear, vibration and shock rather than infer it from the word "worm". */
        attribute :>> urls = ("https://download.sew-eurodrive.com/download/pdf/16934016.pdf");
    }
    dependency sail7Basis from BlueDogDesignDecisions::sizingBaseline to sail7;
    part sail8 : SourceNote {
        doc /* The concern is maintenance-free exposure. North Sails identifies [flogging, flutter and flex fatigue](https://www.northsails.com/en-us/blogs/north-sails-blog/four-fs-sail-fatigue-flex-fiber-compression-flogging-flutter), and recommends [chafe protection, UV protection and inspection](https://www.northsails.com/en-uk/blogs/north-sails-blog/sail-care-maintenance-tips-diy). For the finite Gorge mission, fabric/line wear and autonomous sail handling are comparison criteria alongside rigid-wing bearing, drive and skin risks. The soft sail remains an equal development contender; persistent ocean service is a separate future exposure. A furling or self-locking winch may address some risks, but introduces its own mechanisms and failure cases. */
        attribute :>> urls = ("https://www.northsails.com/en-us/blogs/north-sails-blog/four-fs-sail-fatigue-flex-fiber-compression-flogging-flutter", "https://www.northsails.com/en-uk/blogs/north-sails-blog/sail-care-maintenance-tips-diy");
    }
    dependency sail8Basis from BlueDogDesignDecisions::sizingBaseline to sail8;
    part sail9 : SourceNote {
        doc /* Rigid construction also has real durability limits. Saildrone reports that tall wings were damaged during Southern Ocean attempts; its lower-aspect replacement improved survival while sacrificing upwind capability. That is directly relevant to a mission requiring upstream windward progress. See [Saildrone's account of the Antarctic circumnavigation](https://www.saildrone.com/eu-en/news/unmanned-vehicle-completes-antarctica-circumnavigation). Avoiding sailcloth does not establish wave-impact survival. */
        attribute :>> urls = ("https://www.saildrone.com/eu-en/news/unmanned-vehicle-completes-antarctica-circumnavigation");
    }
    dependency sail9Basis from BlueDogDesignDecisions::sizingBaseline to sail9;
    part regulation10 : SourceNote {
        doc /* | Source | What it establishes | Limit for Blue Dog |
| --- | --- | --- |
| [Boat Length, March 18, 2023](https://groups.google.com/g/microtransat/c/ZCm62dVztJ4) | Paul Miller attributes the 2.4 m overall race limit to a USCG interpretation treating smaller craft as oceanographic devices. | A participant's report; the thread does not supply the underlying agency determination or its conditions. |
| [Microtransat FAQ](https://www.microtransat.org/faq.php) | Organizers report UK/French coastguard conversations supporting buoy classification, but a differing IMO view. | Evidence of differing interpretations, not a current ruling for this project. |
| [2026 race discussion, April 14](https://groups.google.com/g/microtransat/c/DuZiwjFllE8) | Francis Roussel discusses a 2.5 m threshold. | Country, regulatory purpose and conditions matter; length alone is insufficient. |
| [French regulation discussion, August 24-25, 2026](https://groups.google.com/g/microtransat/c/0_jdHs-k-cY) | Participants discuss French maritime-drone rules and contrast the UK MGN 702 exemption. | Do not import the thread's one-metre or nationality conclusions into a US design requirement. |
| [MCA MGN 702 Amendment 2, January 19, 2026](https://www.gov.uk/government/publications/mgn-702-m-amendment-2-maritime-autonomous-surface-ships-of-less-than-25-metres-in-loa/mgn-702-m-amendment-2-maritime-autonomous-surface-ships-of-less-than-25-metres-in-loa) | An actual conditional exemption from specified certification requirements for eligible MASS below 2.5 m. The guidance explicitly retains other maritime requirements. | It still describes these craft as vessels; this is not a US buoy exemption. | */
        attribute :>> urls = ("https://groups.google.com/g/microtransat/c/ZCm62dVztJ4", "https://www.microtransat.org/faq.php", "https://groups.google.com/g/microtransat/c/DuZiwjFllE8", "https://groups.google.com/g/microtransat/c/0_jdHs-k-cY", "https://www.gov.uk/government/publications/mgn-702-m-amendment-2-maritime-autonomous-surface-ships-of-less-than-25-metres-in-loa/mgn-702-m-amendment-2-maritime-autonomous-surface-ships-of-less-than-25-metres-in-loa");
    }
    dependency regulation10Basis from BlueDogRequirements::regulatoryClassification to regulation10;
    part regulation11 : SourceNote {
        doc /* The August thread links [French Decree 2024-461](https://www.legifrance.gouv.fr/jorf/id/JORFTEXT000049583905). It is a useful jurisdiction-specific lead, not authority for the Columbia River. The unresolved US question is the underlying USCG oceanographic-device interpretation: its text, date, purpose, scope and continuing applicability to an autonomous sailing research craft, including powered recovery and station keeping. No correspondence has been sent on the user's behalf. */
        attribute :>> urls = ("https://www.legifrance.gouv.fr/jorf/id/JORFTEXT000049583905");
    }
    dependency regulation11Basis from BlueDogRequirements::regulatoryClassification to regulation11;
    part regulation12 : SourceNote {
        doc /* For now S-005 retains classification review and S-004 retains mode-dependent conspicuity. The source discussion concerns a 2.4 m race limit, which does not establish a legal safe harbor. The current independent Gorge challenge separately imposes the owner-selected 1.2 m overall limit in C-010; neither length establishes regulatory classification. USCG's public FAQ uses transportation capability to explain vessel status, including transportation of services. [USCG navigation FAQ](https://navcen.uscg.gov/navigation-rules-faqs) */
        attribute :>> urls = ("https://navcen.uscg.gov/navigation-rules-faqs");
    }
    dependency regulation12Basis from BlueDogRequirements::regulatoryClassification to regulation12;
    part regulation13 : SourceNote {
        doc /* If an installation is an aid to maritime navigation, 33 CFR 66.01-1 requires permission to establish it. That provision neither declares every scientific buoy an aid nor supplies a blanket exemption for small research platforms. Whether it applies to a proposed observation installation must be resolved for that installation. [33 CFR 66.01-1](https://www.ecfr.gov/current/title-33/chapter-I/subchapter-C/part-66/subpart-66.01/section-66.01-1) */
        attribute :>> urls = ("https://www.ecfr.gov/current/title-33/chapter-I/subchapter-C/part-66/subpart-66.01/section-66.01-1");
    }
    dependency regulation13Basis from BlueDogRequirements::regulatoryClassification to regulation13;
    part regulation14 : SourceNote {
        doc /* Rule 25 contains lighting provisions for sailing vessels below 7 m. Rule 23 contains alternatives for power-driven vessels below 12 m, and narrower conditions for some vessels below 7 m. These are conditional equipment provisions, not maximum allowable dimensions for an unmanned boat. Powered recovery also requires review of the applicable power-driven mode. Inland and International wording must be applied to the correct waters. [USCG amalgamated navigation rules, Rules 3, 23 and 25](https://navcen.uscg.gov/navigation-rules-amalgamated) */
        attribute :>> urls = ("https://navcen.uscg.gov/navigation-rules-amalgamated");
    }
    dependency regulation14Basis from BlueDogRequirements::regulatoryClassification to regulation14;
    part propulsion15 : SourceNote {
        doc /* For an ideal stationary actuator disk, `P_induced = T^(3/2) / sqrt(2 rho A)`. This follows from momentum theory; it omits profile, swirl, motor/controller and installation losses. NASA's treatment explains the ideal disk model and its limitations. [NASA propeller thrust](https://www1.grc.nasa.gov/beginners-guide-to-aeronautics/propeller-thrust/) */
        attribute :>> urls = ("https://www1.grc.nasa.gov/beginners-guide-to-aeronautics/propeller-thrust/");
    }
    dependency propulsion15Basis from RecoveryPropulsionTrade::RecoverySizing to propulsion15;
    part propulsion16 : SourceNote {
        doc /* Use manufacturer data for the actual propeller, intended fluid and RPM range. APC, for example, publishes different RPM limits for different air-propeller families; a generic motor power rating does not establish an acceptable propeller installation. [APC RPM limits](https://www.apcprop.com/technical-information/rpm-limits/) */
        attribute :>> urls = ("https://www.apcprop.com/technical-information/rpm-limits/");
    }
    dependency propulsion16Basis from RecoveryPropulsionTrade::RecoverySizing to propulsion16;
}

package BlueDogStructure {
    private import ScalarValues::*;
    private import RequirementDerivation::*;
    private import ModelingMetadata::refinement;
    private import SI::*;
    doc /* Owner-selected FDM plus wet-layup construction. Acceptance uses qualified material evidence and validated load/functional envelopes.
     * Provisional numerical screening values live in BlueDogStructuralBasis. */
    requirement def <'T-001'> HybridConstruction {
        metadata workStatus : ModelingMetadata::StatusInfo { status = ModelingMetadata::StatusKind::open; }
        doc /* The primary shell structure shall use an FDM substrate with wet-layup glass/epoxy reinforcement. */
        comment conditions /* Owner-selected construction architecture. PETG is the initial candidate, not a qualified material. */
        metadata rationale : ModelingMetadata::Rationale { text = "Owner-selected construction architecture. PETG is the initial candidate, not a qualified material."; }
    }
    requirement hybridConstruction : HybridConstruction;
    dependency basisHybridConstruction from hybridConstruction to BlueDog::DesignIntent { metadata rationale : ModelingMetadata::Rationale { text = "The owner constrains the shell construction process independently of mission performance."; } }
    requirement def <'T-100'> StructuralIntegrity {
        metadata workStatus : ModelingMetadata::StatusInfo { status = ModelingMetadata::StatusKind::open; }
        doc /* The primary structure shall carry its declared limit loads throughout the specified wet exposure. */
        comment conditions /* Apply T-101 through T-109 independently. Current screening allocations do not cover impact, fatigue, buckling or qualified adhesive strength. */
    }
    requirement structuralIntegrity : StructuralIntegrity;
    dependency structuralBasis from structuralIntegrity to BlueDogRequirements::wetMechanicalIntegrity { metadata rationale : ModelingMetadata::Rationale { text = "Changes to wet exposure and joint integrity require review of structural loads, material bounds and test evidence."; } }
    requirement def <'T-101'> BendingStrength {
        metadata workStatus : ModelingMetadata::StatusInfo { status = ModelingMetadata::StatusKind::open; }
        doc /* Each primary structural member shall retain nonnegative bending-strength margin under the applicable limit-load cases. */
        comment conditions /* Assess each member and load direction using qualified wet/jointed allowables. Grounding, ballast inertia and operational loads are distinct cases. The sizing model currently credits glass only; that is an analysis choice. */
        attribute stressPa : Real;
        attribute qualifiedAllowablePa : Real;
        attribute evidenceAccepted : Boolean;
        require constraint acceptance { evidenceAccepted and qualifiedAllowablePa > 0 and RealFunctions::abs(stressPa) <= qualifiedAllowablePa }
    }
    requirement bendingStrength : BendingStrength;
    #derivation connection deriveBendingStrength { end #original source ::> structuralIntegrity; end #derive target ::> bendingStrength; }
    requirement def <'T-102'> AppendageDeflection {
        metadata workStatus : ModelingMetadata::StatusInfo { status = ModelingMetadata::StatusKind::open; }
        doc /* Each wing, keel and rudder shall remain within its validated functional deformation limit under the applicable load cases. */
        comment conditions /* Validate the limit against affected functions: foil/control performance, alignment, clearances and sealing as applicable. The preliminary sizing fraction is a screening assumption, not an accepted limit. Assess each member and direction separately. */
        attribute fraction : Real;
        attribute validatedMaximumFraction : Real;
        attribute limitEvidenceAccepted : Boolean;
        require constraint acceptance { limitEvidenceAccepted and validatedMaximumFraction > 0 and fraction >= 0 and fraction <= validatedMaximumFraction }
    }
    requirement appendageDeflection : AppendageDeflection;
    #derivation connection deriveAppendageDeflection { end #original source ::> structuralIntegrity; end #derive target ::> appendageDeflection; }
    requirement def <'T-103'> HullDeflection {
        metadata workStatus : ModelingMetadata::StatusInfo { status = ModelingMetadata::StatusKind::open; }
        doc /* The hull shall remain within its validated functional deformation limit under the applicable load cases. */
        comment conditions /* Validate the limit against affected functions: foil/control performance, alignment, clearances and sealing as applicable. The preliminary sizing fraction is a screening assumption, not an accepted limit. Assess each member and direction separately. */
        attribute fraction : Real;
        attribute validatedMaximumFraction : Real;
        attribute limitEvidenceAccepted : Boolean;
        require constraint acceptance { limitEvidenceAccepted and validatedMaximumFraction > 0 and fraction >= 0 and fraction <= validatedMaximumFraction }
    }
    requirement hullDeflection : HullDeflection;
    #derivation connection deriveHullDeflection { end #original source ::> structuralIntegrity; end #derive target ::> hullDeflection; }
    requirement def <'T-104'> PanelStrength {
        metadata workStatus : ModelingMetadata::StatusInfo { status = ModelingMetadata::StatusKind::open; }
        doc /* Each hull skin panel shall retain nonnegative bending-strength margin under the applicable differential-pressure cases. */
        comment conditions /* Determine load cases from immersion, wave/slam exposure and compartment pressures for the selected mission and geometry. The 10 kPa sizing screen is provisional, not a complete pressure envelope. */
        attribute stressPa : Real;
        attribute qualifiedAllowablePa : Real;
        attribute evidenceAccepted : Boolean;
        require constraint acceptance { evidenceAccepted and qualifiedAllowablePa > 0 and RealFunctions::abs(stressPa) <= qualifiedAllowablePa }
    }
    requirement panelStrength : PanelStrength;
    #derivation connection derivePanelStrength { end #original source ::> structuralIntegrity; end #derive target ::> panelStrength; }
    requirement def <'T-105'> PanelDeflection {
        metadata workStatus : ModelingMetadata::StatusInfo { status = ModelingMetadata::StatusKind::open; }
        doc /* Each hull skin panel shall remain within its validated functional deformation limit under the applicable load cases. */
        comment conditions /* Validate the limit against affected functions: foil/control performance, alignment, clearances and sealing as applicable. The preliminary sizing fraction is a screening assumption, not an accepted limit. Assess each member and direction separately. */
        attribute fraction : Real;
        attribute validatedMaximumFraction : Real;
        attribute limitEvidenceAccepted : Boolean;
        require constraint acceptance { limitEvidenceAccepted and validatedMaximumFraction > 0 and fraction >= 0 and fraction <= validatedMaximumFraction }
    }
    requirement panelDeflection : PanelDeflection;
    #derivation connection derivePanelDeflection { end #original source ::> structuralIntegrity; end #derive target ::> panelDeflection; }
    requirement def <'T-106'> RootProofLoad {
        metadata workStatus : ModelingMetadata::StatusInfo { status = ModelingMetadata::StatusKind::open; }
        doc /* Each appendage root attachment shall retain its load path under its applicable limit-load proof cases. */
        comment conditions /* Cover operational, handling, grounding and ballast-inertia loads applicable to the selected design. The initial 100 N tip-load and two-times-weight probes are screening cases, not universal requirements. Beam stress alone does not qualify joints or attachments. */
    }
    requirement rootProofLoad : RootProofLoad;
    #derivation connection deriveRootProofLoad { end #original source ::> structuralIntegrity; end #derive target ::> rootProofLoad; }
    requirement def <'T-107'> WetCouponStrength {
        metadata workStatus : ModelingMetadata::StatusInfo { status = ModelingMetadata::StatusKind::open; }
        doc /* Strength allowables credited in structural qualification shall not exceed the qualified wet-conditioned production-laminate bounds. */
        comment conditions /* Establish directional bounds for the selected layup, print, joints and cure process, including exposure and statistical/design reductions. Lower measured strength requires re-analysis or resizing, not rejection against the provisional 50 MPa input. */
        attribute creditedAllowablePa : Real;
        attribute qualifiedAllowablePa : Real;
        attribute evidenceAccepted : Boolean;
        require constraint acceptance { evidenceAccepted and qualifiedAllowablePa > 0 and creditedAllowablePa > 0 and creditedAllowablePa <= qualifiedAllowablePa }
    }
    requirement wetCouponStrength : WetCouponStrength;
    #derivation connection deriveWetCouponStrength { end #original source ::> structuralIntegrity; end #derive target ::> wetCouponStrength; }
    requirement def <'T-108'> WetCouponStiffness {
        metadata workStatus : ModelingMetadata::StatusInfo { status = ModelingMetadata::StatusKind::open; }
        doc /* Stiffness credited in structural qualification shall not exceed the qualified wet-conditioned production-laminate bounds. */
        comment conditions /* Establish directional effective stiffness for the modeled layup, joints and exposure. A lower measured modulus can be accommodated by geometry or reinforcement changes; 10 GPa is an unverified analysis input, not a material acceptance floor. */
        attribute creditedModulusPa : Real;
        attribute qualifiedModulusPa : Real;
        attribute evidenceAccepted : Boolean;
        require constraint acceptance { evidenceAccepted and qualifiedModulusPa > 0 and creditedModulusPa > 0 and creditedModulusPa <= qualifiedModulusPa }
    }
    requirement wetCouponStiffness : WetCouponStiffness;
    #derivation connection deriveWetCouponStiffness { end #original source ::> structuralIntegrity; end #derive target ::> wetCouponStiffness; }
    requirement def <'T-109'> BondProof {
        metadata workStatus : ModelingMetadata::StatusInfo { status = ModelingMetadata::StatusKind::open; }
        doc /* Each representative glass-to-print joint shall retain its load path under its calculated limit-load proof test after N-044 exposure. */
        comment conditions /* No qualified adhesion value is available; bond acceptance remains evidence-gated even when beam margins pass. */
        metadata rationale : ModelingMetadata::Rationale { text = "No qualified adhesion value is available; bond acceptance remains evidence-gated even when beam margins pass."; }
    }
    requirement bondProof : BondProof;
    #derivation connection deriveBondProof { end #original source ::> structuralIntegrity; end #derive target ::> bondProof; }
    requirement def <'T-110'> LoadedFreeboard {
        metadata workStatus : ModelingMetadata::StatusInfo { status = ModelingMetadata::StatusKind::open; }
        doc /* Downflooding openings shall retain positive clearance above the local water surface throughout the applicable intact operating cases. */
        comment conditions /* Evaluate actual openings, loading, heel, pitch and wave motion. A sealed deck edge may immerse without downflooding; the 50 mm deck-edge screen is not proof of this requirement. */
        attribute minimumOpeningClearanceM : Real;
        attribute caseCoverageAccepted : Boolean;
        require constraint acceptance { caseCoverageAccepted and minimumOpeningClearanceM > 0 }
    }
    requirement loadedFreeboard : LoadedFreeboard;
    dependency basisLoadedFreeboard from loadedFreeboard to BlueDogRequirements::capsizeResilience { metadata rationale : ModelingMetadata::Rationale { text = "The selected intact operating cases determine downflooding clearances; a sealed deck edge is not an opening."; } }
    requirement def <'T-111'> ReserveBuoyancy {
        metadata workStatus : ModelingMetadata::StatusInfo { status = ModelingMetadata::StatusKind::open; }
        doc /* The vessel shall retain sufficient buoyancy to support its loaded weight throughout the applicable casualty-flotation cases. */
        comment conditions /* Use the declared flooding, capsize, ingress and recovery exposure cases; account for retained water and lost buoyant volume. Do not credit unsealed infill. The intact 100-percent reserve screen is not a casualty-flotation demonstration. */
        attribute availableBuoyancyN : Real;
        attribute loadedWeightN : Real;
        attribute caseCoverageAccepted : Boolean;
        require constraint acceptance { caseCoverageAccepted and loadedWeightN > 0 and availableBuoyancyN >= loadedWeightN }
    }
    requirement reserveBuoyancy : ReserveBuoyancy;
    dependency flotationPurpose from reserveBuoyancy to GorgeChallenge::casualtyFlotation { metadata rationale : ModelingMetadata::Rationale { text = "Buoyancy assessment supports casualty flotation but does not establish damage stability, retained components or safe retrieval. Changes to casualty cases require a new assessment."; } }
    dependency basisReserveBuoyancy from reserveBuoyancy to BlueDogRequirements::capsizeResilience { metadata rationale : ModelingMetadata::Rationale { text = "Capsize and flooding cases drive the required buoyancy assessment; intact reserve-volume screens do not establish casualty flotation."; } }
    requirement def <'T-112'> LaunchClearance {
        metadata workStatus : ModelingMetadata::StatusInfo { status = ModelingMetadata::StatusKind::open; }
        doc /* The loaded vessel shall retain the site-qualified bottom clearance throughout the selected launch and retrieval paths. */
        comment conditions /* Use surveyed depth, stage/current uncertainty, vessel motion and actual appendage configuration. The 1.5 m depth and 0.3 m clearance used in preliminary sizing do not qualify a site or impose a universal draft limit. */
        attribute availableDepthM : Real;
        attribute immersedDepthM : Real;
        attribute requiredClearanceM : Real;
        attribute siteEvidenceAccepted : Boolean;
        require constraint acceptance { siteEvidenceAccepted and immersedDepthM > 0 and requiredClearanceM > 0 and availableDepthM - immersedDepthM >= requiredClearanceM }
    }
    requirement launchClearance : LaunchClearance;
    dependency basisLaunchClearance from launchClearance to BlueDogRequirements::soloLaunch { metadata rationale : ModelingMetadata::Rationale { text = "The launch concept determines site and appendage clearances; actual surveyed paths must support the one-person launch claim."; } }
    requirement def <'T-113'> PrintTileEnvelope {
        metadata workStatus : ModelingMetadata::StatusInfo { status = ModelingMetadata::StatusKind::open; }
        doc /* Each structural tile shall fit the 250 mm cubic print-job envelope in its selected build configuration. */
        comment conditions /* Include supports, brim, raft and printer clearance in the job extents. The 230 mm tile is a seam/mass-study assumption; larger tiles are permitted when the complete job satisfies P-002. */
        attribute jobXM : Real;
        attribute jobYM : Real;
        attribute jobZM : Real;
        attribute slicerEvidenceAccepted : Boolean;
        require constraint acceptance { slicerEvidenceAccepted and BlueDogRequirements::PrintJobEnvelopeCriterion(jobXM * 1 [m], jobYM * 1 [m], jobZM * 1 [m], BlueDogRequirements::printBuildLimit) }
    }
    requirement printTileEnvelope : PrintTileEnvelope;
    #refinement dependency basisPrintTileEnvelope from printTileEnvelope to BlueDogRequirements::desktopManufacture { metadata rationale : ModelingMetadata::Rationale { text = "Applies the same owner print-job envelope to structural tiles with accepted slicer evidence. The native system predicate supplies the common dimensional bounds."; } }
    // Compatibility projection for numerical adapters; authority is the analysis basis.
    analysis def MaterialInputs :> BlueDogStructuralBasis::Inputs;
    analysis material : MaterialInputs;

    dependency materialSource from MaterialInputs to hybridConstruction { metadata rationale : ModelingMetadata::Rationale { text = "Material input assumptions depend on the owner construction concept; a process change requires new property evidence and analysis inputs."; } }
    satisfy hybridConstruction by BlueDog::Architecture::missionContext.boat.hullAndRig.printedHull;
    satisfy bendingStrength by BlueDog::Architecture::missionContext.boat.hullAndRig;
    satisfy appendageDeflection by BlueDog::Architecture::missionContext.boat.hullAndRig;
    satisfy loadedFreeboard by BlueDog::Architecture::missionContext.boat.hullAndRig.printedHull;
    satisfy reserveBuoyancy by BlueDog::Architecture::missionContext.boat.hullAndRig.printedHull;
    satisfy launchClearance by BlueDog::Architecture::missionContext.boat.hullAndRig;
    satisfy printTileEnvelope by BlueDog::Architecture::missionContext.boat.hullAndRig.printedHull;
}

package BlueDogUseCases {
    private import OOSEM::systemUseCase;
    private import BlueDog::Architecture::*;
    private import BlueDogRequirements::*;
    #systemUseCase use case prepare {
        doc /* Prepare and launch. */
        subject context : MissionContext;
        actor operator : Operator;
        objective 'P-001 Transportability' :> transportability;
    }
    #systemUseCase use case sailGorge {
        doc /* Complete Gorge challenge. */
        subject context : MissionContext;
        actor operator : Operator;
        actor traffic : OtherVessel;
        objective 'M-001 Gorge mission' :> roundTrip;
    }
    #systemUseCase use case navigateCourse {
        doc /* Use current validated navigation to follow the declared course
         * and operating boundaries. Invalid observations require degradation and
         * separately confirmed safety; they cannot silently remain control inputs. */
        subject context : MissionContext;
        actor operator : Operator;
        actor traffic : OtherVessel;
        objective 'E-002 Navigation and control' :> navigationAndControl;
    }
    #systemUseCase use case preserveRecoveryReserve {
        doc /* Observe usable energy and current recovery demand, preserve
         * required safety loads, and transfer to recovery when reserve is threatened. */
        subject context : MissionContext;
        actor operator : Operator;
        objective 'E-004 Low-energy recovery' :> lowEnergyRecovery;
    }
    #systemUseCase use case sailOcean {
        metadata applicability : BlueDogMissionScope::Applicability { mission = BlueDogMissionScope::MissionKind::futureOcean; }
        doc /* Future mission: sail to Hawaii under independently allocated constraints. */
        subject context : MissionContext;
        actor operator : Operator;
        actor traffic : OtherVessel;
        objective 'H-001 Hawaii voyage' :> BlueDog::Goals::hawaiiVoyage;
    }
    #systemUseCase use case monitor {
        doc /* Monitor live and reconnect. */
        subject context : MissionContext;
        actor operator : Operator;
        objective 'C-101 Telemetry' :> telemetryEquipment;
    }
    #systemUseCase use case recover {
        doc /* Abort and recover. */
        subject context : MissionContext;
        actor operator : Operator;
        actor traffic : OtherVessel;
        objective 'S-003 Emergency control' :> emergencyControl;
    }
    #systemUseCase use case recoverUpright {
        doc /* For the passive-righting candidate, retain required safety while inverted, recover upright without
         * propulsion or outside assistance, and restore control without clearing
         * gate progress, restrictions or a prior loss of qualification. If safety
         * is unavailable, transfer to autonomous abort and recovery. */
        subject context : MissionContext;
        actor operator : Operator;
        actor traffic : OtherVessel;
        objective 'N-051 Self-righting' :> selfRighting;
    }
    #systemUseCase use case maintain {
        doc /* Manufacture and service. */
        subject context : MissionContext;
        actor operator : Operator;
        objective 'P-003 Serviceability' :> serviceability;
    }
    #systemUseCase use case avoidTraffic {
        doc /* Detect AIS and non-AIS traffic, assess collision risk, maneuver, and monitor separation without depending on operator intervention or cooperation by the other vessel. */
        subject context : MissionContext;
        actor operator : Operator;
        actor traffic : OtherVessel;
        objective 'S-001 Traffic safety' :> trafficSafety;
    }
    #systemUseCase use case presentNavigationSignals {
        doc /* Present mode-appropriate navigation signals to other vessels during sailing, powered recovery and stationary operation. */
        subject context : MissionContext;
        actor traffic : OtherVessel;
        objective 'S-004 Navigation conspicuity' :> navigationConspicuity;
    }
    dependency poweredRecoveryBasis from recover to BlueDogRequirements::recoveryPropulsion;
}

package BlueDogVerificationPlanning {
    private import ScalarValues::*;
    doc /* Verification-method tags describe plans, not execution or acceptance.
     * Source basis: NASA SE Handbook 5.3.1.2 and 5.4.1.2; NASA-HDBK-1009A
     * 8.14-8.20 engineering information design; defense SE Guidebook 2026
     * 6.2.5-6.2.7. SysML 2.0 VerificationCases supplies method/verdict kinds.
     * Plans remain inconclusive. Historical records retain their own subjects. */

    calc def EvidenceEligibleForAcceptance {
        doc /* Decision-support preconditions only, never an acceptance decision.
         * Inputs are established by traceable evidence review, not inferred from
         * an artifact filename or a successful equation. False eligibility does
         * not discard a valid failed test or prevent review of incomplete data.
         * Criteria and uncertainty rules belong to the actual assessed claim. */
        in executed : Boolean [1];
        in subjectIdentified : Boolean [1];
        in configurationApplicable : Boolean [1];
        in conditionsApplicable : Boolean [1];
        in procedureControlled : Boolean [1];
        in provenanceIntact : Boolean [1];
        in measurementBasisAdequate : Boolean [1];
        in uncertaintyAdequate : Boolean [1];
        in criterionEvaluated : Boolean [1];
        in criterionHolds : Boolean [1];
        in anomaliesAccounted : Boolean [1];
        return eligible : Boolean [1] = executed and subjectIdentified and configurationApplicable
        and conditionsApplicable and procedureControlled and provenanceIntact
        and measurementBasisAdequate and uncertaintyAdequate and criterionEvaluated
        and criterionHolds and anomaliesAccounted;
    }
    part def PlannedTestConfiguration {
        ref part plannedDesign : MarineDesign::Design [1];
        ref part plannedAssembly : BlueDogPhysicalArchitecture::IC01Candidate [1];
        attribute purpose : String [1];
        attribute articleIdentity : String [0..1];
        attribute procedureIdentity : String [0..1];
        attribute instrumentConfiguration : String [0..1];
        attribute plannedOnly : Boolean = true;
        doc /* Planned candidate references are not the identity of a built article.
         * Absent article, released procedure and instruments remain unresolved;
         * no execution or evidence-acceptance status is invented. */
    }
    part interfaceBench : PlannedTestConfiguration {
        ref part :>> plannedDesign = BlueDogIC01::design;
        ref part :>> plannedAssembly = BlueDogPhysicalArchitecture::ic01;
        attribute :>> purpose = "Current Gorge command/permission, storage durability and restart integration";
    }
    part recoveryUseTrial : PlannedTestConfiguration {
        ref part :>> plannedDesign = BlueDogIC01::design;
        ref part :>> plannedAssembly = BlueDogPhysicalArchitecture::ic01;
        attribute :>> purpose = "Current Gorge recovery approach, shore retention and one-person pickup in admitted conditions";
    }
    verification def InterfaceAndDurabilityIntegrationVerification {
        metadata plannedTest : VerificationCases::VerificationMethod { kind = VerificationCases::VerificationMethodKind::test; }
        metadata plannedInspect : VerificationCases::VerificationMethod { kind = VerificationCases::VerificationMethodKind::inspect; }
        subject vessel : BlueDogPhysicalArchitecture::IC01Candidate = BlueDogPhysicalArchitecture::ic01;
        doc /* Freeze actual article/software/storage/clock configuration and procedure.
         * Independently observe command receipt, authority/expiry assessment,
         * durable disqualification acknowledgment and physical motor enable.
         * Inject stale/future/reordered/replayed commands, expired permissions,
         * missing acknowledgments, primary loss and reset between each boundary.
         * Confirm no thrust while qualification is qualifying or unknown and no
         * commanded enable before durable disqualification. Establish legitimate
         * onboard recovery authorization separately from authenticated operator
         * authorization. Measure the governed restart/response deadlines using
         * appropriate instrumentation; synthetic gate checks do not close them.
         * Retain failures, input loss and power-cut corruption, not only clean runs. */
        objective acceptance {
            verify BlueDogRequirements::motorQualificationInvariant;
            verify BlueDogRequirements::freshRecoveryCommand;
            verify BlueDogRequirements::qualificationPersistence;
            verify BlueDogRequirements::qualificationRestoration;
        }
        return verdict : VerificationCases::VerdictKind = VerificationCases::VerdictKind::inconclusive;
    }
    verification def HumanRecoveryUseValidation {
        metadata plannedTest : VerificationCases::VerificationMethod { kind = VerificationCases::VerificationMethodKind::test; }
        metadata plannedDemo : VerificationCases::VerificationMethod { kind = VerificationCases::VerificationMethodKind::demo; }
        subject vessel : BlueDogPhysicalArchitecture::IC01Candidate = BlueDogPhysicalArchitecture::ic01;
        doc /* Combined product verification and stakeholder-use validation.
         * Use the identified actual operator, candidate installation, handling
         * aids and surveyed recovery destination. Declare conditions, access,
         * retrieval exposure, acceptance criteria and recovery arrangements before
         * the trial. Observe autonomous approach separately from shore capture,
         * retention and one-person pickup. Measure applicable handling outcomes;
         * assess whether the intended user can complete the whole recovery task.
         * Record failures, assistance, unsafe access and incomplete retrieval.
         * A simulated approach, propulsion command or cooperative fixture alone
         * cannot establish intended-use recovery or physical qualification. */
        objective acceptance { verify BlueDogRequirements::soloRetrieval; }
        return verdict : VerificationCases::VerdictKind = VerificationCases::VerdictKind::inconclusive;
    }
    dependency interfaceConfiguration from interfaceBench to InterfaceAndDurabilityIntegrationVerification;
    dependency recoveryConfiguration from recoveryUseTrial to HumanRecoveryUseValidation;
    dependency intendedRecoveryUse from HumanRecoveryUseValidation to BlueDogUseCases::recover;
    dependency interfaceScenario from InterfaceAndDurabilityIntegrationVerification to BlueDogMethod::Scenarios::AbortAndRecover;
    dependency restartContract from InterfaceAndDurabilityIntegrationVerification to BlueDogBehaviorContracts::RestoreQualification;
    metadata issue : ModelingMetadata::Issue {
        text = "V-01: Release configuration-specific procedures, article identity, instrumentation/calibration and acceptance criteria before physical assessment. V-02: Establish applicability and uncertainty for every transferred component, historical or simulation artifact. V-03: Retain independent review and acceptance dispositions; method tags and eligibility checks do not execute or accept evidence. V-04: Perform stakeholder-use validation of shore capture, retention and one-person pickup, not only autonomous approach.";
    }
}

package BlueDogRequirementVerification {
    doc /* Verification specifications, not completed evidence. Each case remains
     * inconclusive until an evidence-backed implementation supplies a verdict.
     * Named requirement conditions are normative qualification definitions;
     * rationale and notes are explanatory. */
    verification def <'V-M-001'> RoundTripVerification {
        metadata plannedTest : VerificationCases::VerificationMethod { kind = VerificationCases::VerificationMethodKind::test; }
        metadata plannedAnalyze : VerificationCases::VerificationMethod { kind = VerificationCases::VerificationMethodKind::analyze; }
        doc /* Apply the complete M-001 qualification conditions and GorgeChallengeVerification::PassageQualificationVerification acceptance strategy. Correlate the observed trajectory with safety-capability, energy-reserve, external-command, propulsion and qualification histories. Test safe unassisted righting separately from capsize with safety loss, motor use or external assistance. Missing gate crossings, missing evidence or disqualifying events prevent a completion verdict. */
        objective acceptance {
            verify BlueDogRequirements::roundTrip;
        }
        return verdict : VerificationCases::VerdictKind = VerificationCases::VerdictKind::inconclusive;
    }
    verification def <'V-M-002'> MultiDayEnduranceVerification {
        metadata plannedTest : VerificationCases::VerificationMethod { kind = VerificationCases::VerificationMethodKind::test; }
        metadata plannedAnalyze : VerificationCases::VerificationMethod { kind = VerificationCases::VerificationMethodKind::analyze; }
        doc /* Apply the M-002 qualification conditions. Record initial battery state, harvester configuration, resource profile, harvested energy and loads. Limit input to installed-harvester output measured under a frozen, recorded resource profile; any test supply replay must not exceed measured power or accumulated energy. Absent profile evidence invalidates the test. */
        objective acceptance {
            verify BlueDogRequirements::multiDayEndurance;
        }
        return verdict : VerificationCases::VerdictKind = VerificationCases::VerdictKind::inconclusive;
    }
    verification def <'V-E-001'> EnergyAwarenessVerification {
        metadata plannedTest : VerificationCases::VerificationMethod { kind = VerificationCases::VerificationMethodKind::test; }
        metadata plannedAnalyze : VerificationCases::VerificationMethod { kind = VerificationCases::VerificationMethodKind::analyze; }
        doc /* Apply the E-001 qualification conditions. Assess every applicable acceptance outcome separately: E-101, E-102, E-103, E-104. */
        objective acceptance {
            verify BlueDogRequirements::energyAwareness;
            verify BlueDogRequirements::energyEstimateCadence;
            verify BlueDogRequirements::reserveEstimateCadence;
            verify BlueDogRequirements::energyEstimateAccuracy;
            verify BlueDogRequirements::conservativeEnergyEstimate;
        }
        return verdict : VerificationCases::VerdictKind = VerificationCases::VerdictKind::inconclusive;
    }
    verification def <'V-E-002'> NavigationAndControlVerification {
        metadata plannedTest : VerificationCases::VerificationMethod { kind = VerificationCases::VerificationMethodKind::test; }
        metadata plannedAnalyze : VerificationCases::VerificationMethod { kind = VerificationCases::VerificationMethodKind::analyze; }
        doc /* Apply the E-002 qualification conditions. Assess every applicable acceptance outcome separately: E-105, E-106, E-107, E-108, E-109. */
        objective acceptance {
            verify BlueDogRequirements::navigationAndControl;
            verify BlueDogRequirements::guidanceUpdateCadence;
            verify BlueDogRequirements::sailCommandCadence;
            verify BlueDogRequirements::steeringCommandCadence;
            verify BlueDogRequirements::positionAccuracy;
            verify BlueDogRequirements::headingAccuracy;
        }
        return verdict : VerificationCases::VerdictKind = VerificationCases::VerdictKind::inconclusive;
    }
    verification def <'V-E-003'> ResetRecoveryVerification {
        metadata plannedTest : VerificationCases::VerificationMethod { kind = VerificationCases::VerificationMethodKind::test; }
        doc /* Apply the E-003 qualification conditions. Assess every applicable acceptance outcome separately: E-110, E-111, E-112, E-113, E-145, E-136, E-139, E-138, R-102, R-101. */
        objective acceptance {
            verify BlueDogRequirements::resetRecovery;
            verify BlueDogRequirements::restartDeadline;
            verify BlueDogRequirements::missionStateRestoration;
            verify BlueDogRequirements::gateProgressRestoration;
            verify BlueDogRequirements::resetRestrictionPreservation;
            verify BlueDogRequirements::qualificationRestoration;
            verify BlueDogRequirements::logInterruptionDurability;
            verify BlueDogRequirements::unknownQualificationFallback;
            verify BlueDogRequirements::qualificationPersistence;
            verify BlueDogRequirements::freshRecoveryCommand;
            verify BlueDogRequirements::motorQualificationInvariant;
        }
        return verdict : VerificationCases::VerdictKind = VerificationCases::VerdictKind::inconclusive;
    }
    verification def <'V-E-004'> LowEnergyRecoveryVerification {
        metadata plannedTest : VerificationCases::VerificationMethod { kind = VerificationCases::VerificationMethodKind::test; }
        metadata plannedAnalyze : VerificationCases::VerificationMethod { kind = VerificationCases::VerificationMethodKind::analyze; }
        doc /* Apply the E-004 qualification conditions. Assess every applicable acceptance outcome separately: E-114, E-115, E-116, E-117, E-118, E-119, E-130, E-120, E-132, R-101. */
        objective acceptance {
            verify BlueDogRequirements::lowEnergyRecovery;
            verify BlueDogRequirements::lowEnergyEntry;
            verify BlueDogRequirements::lowEnergyPayloadInhibition;
            verify BlueDogRequirements::lowEnergyNavigationContinuity;
            verify BlueDogRequirements::lowEnergyCollisionContinuity;
            verify BlueDogRequirements::lowEnergyExit;
            verify BlueDogRequirements::payloadRestartPermission;
            verify BlueDogRequirements::periodicLogCadence;
            verify BlueDogRequirements::telemetryDeliveryCadence;
            verify BlueDogRequirements::criticalEventRecording;
            verify BlueDogRequirements::motorQualificationInvariant;
        }
        return verdict : VerificationCases::VerdictKind = VerificationCases::VerdictKind::inconclusive;
    }
    verification def <'V-E-005'> CommunicationsVerification {
        metadata plannedTest : VerificationCases::VerificationMethod { kind = VerificationCases::VerificationMethodKind::test; }
        doc /* Apply the E-005 qualification conditions. Assess every applicable acceptance outcome separately: E-120, E-121, E-122, E-123, E-124, E-131, E-137. */
        objective acceptance {
            verify BlueDogRequirements::communications;
            verify BlueDogRequirements::telemetryDeliveryCadence;
            verify BlueDogRequirements::outageAutonomy;
            verify BlueDogRequirements::reconnectCurrentRecord;
            verify BlueDogRequirements::backlogOrdering;
            verify BlueDogRequirements::backlogCurrentPriority;
            verify BlueDogRequirements::logRetention;
            verify BlueDogRequirements::reconnectLogPreservation;
        }
        return verdict : VerificationCases::VerdictKind = VerificationCases::VerdictKind::inconclusive;
    }
    verification def <'V-E-006'> IngressResponseVerification {
        metadata plannedTest : VerificationCases::VerificationMethod { kind = VerificationCases::VerificationMethodKind::test; }
        doc /* Apply the E-006 qualification conditions. Assess every applicable acceptance outcome separately: E-125, E-126, E-127, E-128, E-129, E-144, E-132, R-101. */
        objective acceptance {
            verify BlueDogRequirements::ingressResponse;
            verify BlueDogRequirements::ingressDetection;
            verify BlueDogRequirements::ingressRecoveryRequest;
            verify BlueDogRequirements::ingressFlotation;
            verify BlueDogRequirements::ingressElectronicsProtection;
            verify BlueDogRequirements::ingressPositionContinuity;
            verify BlueDogRequirements::ingressEventDeadline;
            verify BlueDogRequirements::criticalEventRecording;
            verify BlueDogRequirements::motorQualificationInvariant;
        }
        return verdict : VerificationCases::VerdictKind = VerificationCases::VerdictKind::inconclusive;
    }
    verification def <'V-E-007'> MissionEvidenceVerification {
        metadata plannedTest : VerificationCases::VerificationMethod { kind = VerificationCases::VerificationMethodKind::test; }
        metadata plannedInspect : VerificationCases::VerificationMethod { kind = VerificationCases::VerificationMethodKind::inspect; }
        doc /* Apply the E-007 qualification conditions. Assess every applicable acceptance outcome separately: E-130, E-131, E-132, E-133, E-134, E-135, E-136, E-137, E-138, E-139. */
        objective acceptance {
            verify BlueDogRequirements::missionEvidence;
            verify BlueDogRequirements::periodicLogCadence;
            verify BlueDogRequirements::logRetention;
            verify BlueDogRequirements::criticalEventRecording;
            verify BlueDogRequirements::logTimestampAccuracy;
            verify BlueDogRequirements::invalidTimestampMarking;
            verify BlueDogRequirements::logGapIndication;
            verify BlueDogRequirements::logInterruptionDurability;
            verify BlueDogRequirements::reconnectLogPreservation;
            verify BlueDogRequirements::qualificationPersistence;
            verify BlueDogRequirements::unknownQualificationFallback;
        }
        return verdict : VerificationCases::VerdictKind = VerificationCases::VerdictKind::inconclusive;
    }
    verification def <'V-P-001'> TransportabilityVerification {
        metadata plannedTest : VerificationCases::VerificationMethod { kind = VerificationCases::VerificationMethodKind::test; }
        metadata plannedInspect : VerificationCases::VerificationMethod { kind = VerificationCases::VerificationMethodKind::inspect; }
        doc /* Apply the P-001 qualification conditions. Assess every applicable acceptance outcome separately: P-101, P-102, P-103, P-104, P-105, P-106. */
        objective acceptance {
            verify BlueDogRequirements::transportability;
            verify BlueDogRequirements::soloTransport;
            verify BlueDogRequirements::liftMass;
            verify BlueDogRequirements::setupDuration;
            verify BlueDogRequirements::packDuration;
            verify BlueDogRequirements::soloLaunch;
            verify BlueDogRequirements::soloRetrieval;
        }
        return verdict : VerificationCases::VerdictKind = VerificationCases::VerdictKind::inconclusive;
    }
    verification def <'V-P-002'> DesktopManufactureVerification {
        metadata plannedInspect : VerificationCases::VerificationMethod { kind = VerificationCases::VerificationMethodKind::inspect; }
        metadata plannedAnalyze : VerificationCases::VerificationMethod { kind = VerificationCases::VerificationMethodKind::analyze; }
        doc /* Apply the P-002 qualification conditions. Compare slicer/job-envelope measurements for every job with the 250 × 250 × 250 mm usable Cartesian travel; raw part volume is insufficient. */
        objective acceptance {
            verify BlueDogRequirements::desktopManufacture;
        }
        return verdict : VerificationCases::VerdictKind = VerificationCases::VerdictKind::inconclusive;
    }
    verification def <'V-P-003'> ServiceabilityVerification {
        metadata plannedTest : VerificationCases::VerificationMethod { kind = VerificationCases::VerificationMethodKind::test; }
        metadata plannedInspect : VerificationCases::VerificationMethod { kind = VerificationCases::VerificationMethodKind::inspect; }
        doc /* Apply the P-003 qualification conditions. Assess every applicable acceptance outcome separately: P-107, P-108, P-109, P-110. */
        objective acceptance {
            verify BlueDogRequirements::serviceability;
            verify BlueDogRequirements::replacementDuration;
            verify BlueDogRequirements::nondestructiveService;
            verify BlueDogRequirements::postServiceSealing;
            verify BlueDogRequirements::postServiceActuation;
        }
        return verdict : VerificationCases::VerdictKind = VerificationCases::VerdictKind::inconclusive;
    }
    verification def <'V-S-001'> TrafficSafetyVerification {
        metadata plannedTest : VerificationCases::VerificationMethod { kind = VerificationCases::VerificationMethodKind::test; }
        metadata plannedAnalyze : VerificationCases::VerificationMethod { kind = VerificationCases::VerificationMethodKind::analyze; }
        doc /* Verify S-001 and its decomposed timing and tracking requirements using reviewed class-specific and conservative unclassified envelopes from BlueDogClassDetection. Record class/condition-specific timely track and whole-response probability lower bounds, confidence, applicable method and consequence/exposure reviews, classification transitions, clearance and risk disposition. Independently observe collision and nonimpediment obligations; source-model gates and synthetic truth do not demonstrate physical compliance. Current allocations and installed evidence remain open.*/
        objective acceptance {
            verify BlueDogRequirements::trafficSafety;
            verify BlueDogRequirements::trafficTracking;
            verify BlueDogRequirements::collisionAssessmentCadence;
            verify BlueDogRequirements::avoidanceCommandDeadline;
            verify BlueDogRequirements::trafficAwarenessFault;
        }
        return verdict : VerificationCases::VerdictKind = VerificationCases::VerdictKind::inconclusive;
    }
    verification def <'V-S-002'> OperatingBoundaryVerification {
        metadata plannedTest : VerificationCases::VerificationMethod { kind = VerificationCases::VerificationMethodKind::test; }
        metadata plannedAnalyze : VerificationCases::VerificationMethod { kind = VerificationCases::VerificationMethodKind::analyze; }
        doc /* Apply the S-002 qualification conditions. Assess every applicable acceptance outcome separately: S-105, S-106, S-107, S-108, S-109. */
        objective acceptance {
            verify BlueDogRequirements::operatingBoundary;
            verify BlueDogRequirements::boundaryEvaluationCadence;
            verify BlueDogRequirements::boundaryAvoidanceDeadline;
            verify BlueDogRequirements::boundaryAvoidanceRecording;
            verify BlueDogRequirements::boundaryStartInhibition;
            verify BlueDogRequirements::boundaryDegradedEvidence;
        }
        return verdict : VerificationCases::VerdictKind = VerificationCases::VerdictKind::inconclusive;
    }
    verification def <'V-S-003'> EmergencyControlVerification {
        metadata plannedTest : VerificationCases::VerificationMethod { kind = VerificationCases::VerificationMethodKind::test; }
        doc /* Apply the S-003 qualification conditions. Assess every applicable acceptance outcome separately: S-110, S-111, S-112, S-113, S-114, S-115, E-138, R-101, E-130. */
        objective acceptance {
            verify BlueDogRequirements::emergencyControl;
            verify BlueDogRequirements::abortLatchDeadline;
            verify BlueDogRequirements::recoveryTelemetryCadence;
            verify BlueDogRequirements::motorIsolationDeadline;
            verify BlueDogRequirements::isolationRestartInhibition;
            verify BlueDogRequirements::manualControlLossShutdown;
            verify BlueDogRequirements::controlLossLocationContinuity;
            verify BlueDogRequirements::qualificationPersistence;
            verify BlueDogRequirements::motorQualificationInvariant;
            verify BlueDogRequirements::periodicLogCadence;
        }
        return verdict : VerificationCases::VerdictKind = VerificationCases::VerdictKind::inconclusive;
    }
    verification def <'V-S-004'> NavigationConspicuityVerification {
        metadata plannedTest : VerificationCases::VerificationMethod { kind = VerificationCases::VerificationMethodKind::test; }
        metadata plannedInspect : VerificationCases::VerificationMethod { kind = VerificationCases::VerificationMethodKind::inspect; }
        doc /* Apply the S-004 qualification conditions. Assess every applicable acceptance outcome separately: S-116, S-117, S-118, S-119, S-120, S-121. */
        objective acceptance {
            verify BlueDogRequirements::navigationConspicuity;
            verify BlueDogRequirements::navigationLightPresentation;
            verify BlueDogRequirements::navigationShapePresentation;
            verify BlueDogRequirements::navigationSoundPresentation;
            verify BlueDogRequirements::signalingModeDeadline;
            verify BlueDogRequirements::signalingFaultRecording;
            verify BlueDogRequirements::signalingFaultReporting;
        }
        return verdict : VerificationCases::VerdictKind = VerificationCases::VerdictKind::inconclusive;
    }
    verification def <'V-S-005'> RegulatoryClassificationVerification {
        metadata plannedInspect : VerificationCases::VerificationMethod { kind = VerificationCases::VerificationMethodKind::inspect; }
        doc /* Apply the S-005 qualification conditions. Assess every applicable acceptance outcome separately: S-122, S-123. */
        objective acceptance {
            verify BlueDogRequirements::regulatoryClassification;
            verify BlueDogRequirements::deploymentComplianceRecord;
            verify BlueDogRequirements::deploymentReleaseGate;
        }
        return verdict : VerificationCases::VerdictKind = VerificationCases::VerdictKind::inconclusive;
    }
    verification def <'V-N-001'> EnvironmentalEnvelopeVerification {
        metadata plannedTest : VerificationCases::VerificationMethod { kind = VerificationCases::VerificationMethodKind::test; }
        metadata plannedAnalyze : VerificationCases::VerificationMethod { kind = VerificationCases::VerificationMethodKind::analyze; }
        doc /* Select the current Gorge profile and record configuration, load state, exposure duration, instrumentation and acceptance criteria before testing. Exercise required functions concurrently in physically realizable operating and recovery wind/wave/current combinations. Include N-014 course-derived recovery exposure, the complete N-041 freshwater/spray history and N-043 enclosure immersion checks before and after exposure. Inspect retained safety capability and distinguish structural survival from safe autonomous continuation. Shared equipment tests support the installed-vessel argument only with justified applicability. Ocean profiles require their own future plan and are not accepted by this case. */
        objective acceptance {
            verify BlueDogRequirements::environmentalEnvelope;
            verify BlueDogRequirements::gorgeEnvironment;
            verify BlueDogRequirements::gorgeSurvivalWind;
            verify BlueDogRequirements::freshwaterExposure;
            verify BlueDogRequirements::enclosureSealing;
        }
        return verdict : VerificationCases::VerdictKind = VerificationCases::VerdictKind::inconclusive;
    }
    verification def <'V-N-002'> MarineDurabilityVerification {
        metadata plannedTest : VerificationCases::VerificationMethod { kind = VerificationCases::VerificationMethodKind::test; }
        doc /* Apply the N-002 qualification conditions. Perform post-exposure functional checks for the selected profile. */
        objective acceptance {
            verify BlueDogRequirements::marineDurability;
        }
        return verdict : VerificationCases::VerdictKind = VerificationCases::VerdictKind::inconclusive;
    }
    verification def <'V-R-001'> RecoveryPropulsionVerification {
        metadata plannedTest : VerificationCases::VerificationMethod { kind = VerificationCases::VerificationMethodKind::test; }
        metadata plannedAnalyze : VerificationCases::VerificationMethod { kind = VerificationCases::VerificationMethodKind::analyze; }
        doc /* Apply the R-001 qualification conditions. Measure track, current and electrical power. */
        objective acceptance {
            verify BlueDogRequirements::recoveryPropulsion;
        }
        return verdict : VerificationCases::VerdictKind = VerificationCases::VerdictKind::inconclusive;
    }
    verification def <'V-R-002'> RecoveryEnergyVerification {
        metadata plannedTest : VerificationCases::VerificationMethod { kind = VerificationCases::VerificationMethodKind::test; }
        metadata plannedAnalyze : VerificationCases::VerificationMethod { kind = VerificationCases::VerificationMethodKind::analyze; }
        doc /* Apply the R-002 qualification conditions. Evaluate recovery routes along the course under declared adverse current and casualty conditions. Measure motor and essential powers, bound transit and retrieval exposure, and characterize available battery energy at the lowest operating temperature and end-of-service capacity. Infeasible routes or missing route evidence cannot pass. */
        objective acceptance {
            verify BlueDogRequirements::recoveryEnergy;
        }
        return verdict : VerificationCases::VerdictKind = VerificationCases::VerdictKind::inconclusive;
    }
    verification def <'V-C-101'> TelemetryEquipmentVerification {
        metadata plannedTest : VerificationCases::VerificationMethod { kind = VerificationCases::VerificationMethodKind::test; }
        doc /* Apply the C-101 qualification conditions. Assess every applicable acceptance outcome separately: C-201, C-202, C-203, C-204. */
        objective acceptance {
            verify BlueDogRequirements::telemetryEquipment;
            verify BlueDogRequirements::telemetryDisplayContent;
            verify BlueDogRequirements::telemetryStaleIndication;
            verify BlueDogRequirements::telemetryIdentityPreservation;
            verify BlueDogRequirements::telemetryDuplicateSuppression;
        }
        return verdict : VerificationCases::VerdictKind = VerificationCases::VerdictKind::inconclusive;
    }
    verification def <'V-C-102'> CommandIntegrityVerification {
        metadata plannedTest : VerificationCases::VerificationMethod { kind = VerificationCases::VerificationMethodKind::test; }
        doc /* Apply the C-102 qualification conditions. Assess every applicable acceptance outcome separately: C-205, C-206, C-207, C-208, C-209, C-210, C-211, E-132, E-138. */
        objective acceptance {
            verify BlueDogRequirements::commandIntegrity;
            verify BlueDogRequirements::unauthenticatedCommandRejection;
            verify BlueDogRequirements::replayCommandRejection;
            verify BlueDogRequirements::expiredCommandRejection;
            verify BlueDogRequirements::acceptedCommandDeadline;
            verify BlueDogRequirements::onboardAcknowledgmentDeadline;
            verify BlueDogRequirements::acknowledgmentQueueing;
            verify BlueDogRequirements::externalControlDisqualification;
            verify BlueDogRequirements::criticalEventRecording;
            verify BlueDogRequirements::qualificationPersistence;
        }
        return verdict : VerificationCases::VerdictKind = VerificationCases::VerdictKind::inconclusive;
    }
    verification def <'V-N-011'> GorgeWindVerification {
        metadata plannedTest : VerificationCases::VerificationMethod { kind = VerificationCases::VerificationMethodKind::test; }
        doc /* Apply the N-011 qualification conditions. Include upwind, crosswind and downwind headings. */
        objective acceptance {
            verify BlueDogRequirements::gorgeWind;
        }
        return verdict : VerificationCases::VerdictKind = VerificationCases::VerdictKind::inconclusive;
    }
    verification def <'V-N-012'> GorgeWavesVerification {
        metadata plannedTest : VerificationCases::VerificationMethod { kind = VerificationCases::VerificationMethodKind::test; }
        doc /* Apply the N-012 qualification conditions. Include head, beam and following seas and physically realizable wind-wave-current combinations within the selected profile. */
        objective acceptance {
            verify BlueDogRequirements::gorgeWaves;
        }
        return verdict : VerificationCases::VerdictKind = VerificationCases::VerdictKind::inconclusive;
    }
    verification def <'V-N-013'> GorgeCurrentVerification {
        metadata plannedTest : VerificationCases::VerificationMethod { kind = VerificationCases::VerificationMethodKind::test; }
        doc /* Apply the N-013 qualification conditions. Include opposing current. */
        objective acceptance {
            verify BlueDogRequirements::gorgeCurrent;
        }
        return verdict : VerificationCases::VerdictKind = VerificationCases::VerdictKind::inconclusive;
    }
    verification def <'V-N-015'> GorgeSurvivalWavesVerification {
        metadata plannedTest : VerificationCases::VerificationMethod { kind = VerificationCases::VerificationMethodKind::test; }
        doc /* Apply the N-015 qualification conditions. Include adverse relative directions and physically realizable combinations with profile survival wind and current. */
        objective acceptance {
            verify BlueDogRequirements::gorgeSurvivalWaves;
        }
        return verdict : VerificationCases::VerdictKind = VerificationCases::VerdictKind::inconclusive;
    }
    verification def <'V-N-021'> OceanWindVerification {
        metadata plannedTest : VerificationCases::VerificationMethod { kind = VerificationCases::VerificationMethodKind::test; }
        doc /* Apply the N-021 qualification conditions. Include upwind, crosswind and downwind headings. */
        objective acceptance {
            verify BlueDogRequirements::oceanWind;
        }
        return verdict : VerificationCases::VerdictKind = VerificationCases::VerdictKind::inconclusive;
    }
    verification def <'V-N-022'> OceanWavesVerification {
        metadata plannedTest : VerificationCases::VerificationMethod { kind = VerificationCases::VerificationMethodKind::test; }
        doc /* Apply the N-022 qualification conditions. Include head, beam and following seas and physically realizable wind-wave-current combinations within the selected profile. */
        objective acceptance {
            verify BlueDogRequirements::oceanWaves;
        }
        return verdict : VerificationCases::VerdictKind = VerificationCases::VerdictKind::inconclusive;
    }
    verification def <'V-N-023'> OceanCurrentVerification {
        metadata plannedTest : VerificationCases::VerificationMethod { kind = VerificationCases::VerificationMethodKind::test; }
        doc /* Apply the N-023 qualification conditions. Include opposing current. */
        objective acceptance {
            verify BlueDogRequirements::oceanCurrent;
        }
        return verdict : VerificationCases::VerdictKind = VerificationCases::VerdictKind::inconclusive;
    }
    verification def <'V-N-025'> OceanSurvivalWavesVerification {
        metadata plannedTest : VerificationCases::VerificationMethod { kind = VerificationCases::VerificationMethodKind::test; }
        doc /* Apply the N-025 qualification conditions. Include adverse relative directions and physically realizable combinations with profile survival wind and current. */
        objective acceptance {
            verify BlueDogRequirements::oceanSurvivalWaves;
        }
        return verdict : VerificationCases::VerdictKind = VerificationCases::VerdictKind::inconclusive;
    }
    verification def <'V-N-030'> AirTemperatureVerification {
        metadata plannedTest : VerificationCases::VerificationMethod { kind = VerificationCases::VerificationMethodKind::test; }
        doc /* Apply the N-030 qualification conditions. Test powered cold and hot endpoints after internal temperatures stabilize to less than 1 degC change per hour; operate for 2 hours at each endpoint. */
        objective acceptance {
            verify BlueDogRequirements::airTemperature;
        }
        return verdict : VerificationCases::VerdictKind = VerificationCases::VerdictKind::inconclusive;
    }
    verification def <'V-N-031'> WaterTemperatureVerification {
        metadata plannedTest : VerificationCases::VerificationMethod { kind = VerificationCases::VerificationMethodKind::test; }
        doc /* Apply the N-031 qualification conditions. Operate for 2 hours at each endpoint after thermal stabilization. */
        objective acceptance {
            verify BlueDogRequirements::waterTemperature;
        }
        return verdict : VerificationCases::VerdictKind = VerificationCases::VerdictKind::inconclusive;
    }
    verification def <'V-N-032'> HumidityVerification {
        metadata plannedTest : VerificationCases::VerificationMethod { kind = VerificationCases::VerificationMethodKind::test; }
        doc /* Apply the N-032 qualification conditions. Apply three powered 24-hour cycles between 10 and 40 degC at at least 95 percent relative humidity. Produce visible external condensation during cooling; no liquid water may reach enclosed electronics. */
        objective acceptance {
            verify BlueDogRequirements::humidity;
        }
        return verdict : VerificationCases::VerdictKind = VerificationCases::VerdictKind::inconclusive;
    }
    verification def <'V-N-033'> VisibilityVerification {
        metadata plannedTest : VerificationCases::VerificationMethod { kind = VerificationCases::VerificationMethodKind::test; }
        metadata plannedAnalyze : VerificationCases::VerificationMethod { kind = VerificationCases::VerificationMethodKind::analyze; }
        doc /* Apply the N-033 qualification conditions. Assess every applicable acceptance outcome separately: N-101, N-102, N-103, N-104, N-105. */
        objective acceptance {
            verify BlueDogRequirements::visibility;
            verify BlueDogRequirements::visibilityNavigationCapability;
            verify BlueDogRequirements::visibilityTrafficCapability;
            verify BlueDogRequirements::restrictedVisibilityEntry;
            verify BlueDogRequirements::restrictedVisibilityEvidence;
            verify BlueDogRequirements::restrictedVisibilityCollisionAssessment;
        }
        return verdict : VerificationCases::VerdictKind = VerificationCases::VerdictKind::inconclusive;
    }
    verification def <'V-N-034'> CalmOperationVerification {
        metadata plannedTest : VerificationCases::VerificationMethod { kind = VerificationCases::VerificationMethodKind::test; }
        doc /* Apply the N-034 qualification conditions. Record initial energy, the load measurement and the full energy history. */
        objective acceptance {
            verify BlueDogRequirements::calmOperation;
        }
        return verdict : VerificationCases::VerdictKind = VerificationCases::VerdictKind::inconclusive;
    }
    verification def <'V-N-035'> EnvelopeTransitionVerification {
        metadata plannedTest : VerificationCases::VerificationMethod { kind = VerificationCases::VerificationMethodKind::test; }
        doc /* Apply the N-035 qualification conditions. Assess every applicable acceptance outcome separately: N-106, N-107, N-108, N-109, N-110, E-130, R-101. */
        objective acceptance {
            verify BlueDogRequirements::envelopeTransition;
            verify BlueDogRequirements::survivalEntryDeadline;
            verify BlueDogRequirements::survivalTransitionRecording;
            verify BlueDogRequirements::sailingResumptionDeadline;
            verify BlueDogRequirements::sailingResumptionInhibition;
            verify BlueDogRequirements::resumptionBlockEvidence;
            verify BlueDogRequirements::periodicLogCadence;
            verify BlueDogRequirements::motorQualificationInvariant;
        }
        return verdict : VerificationCases::VerdictKind = VerificationCases::VerdictKind::inconclusive;
    }
    verification def <'V-N-044'> WetMechanicalIntegrityVerification {
        metadata plannedTest : VerificationCases::VerificationMethod { kind = VerificationCases::VerificationMethodKind::test; }
        doc /* Apply the N-044 qualification conditions. Assess every applicable acceptance outcome separately: N-111, N-112. */
        objective acceptance {
            verify BlueDogRequirements::wetMechanicalIntegrity;
            verify BlueDogRequirements::wetMechanismTravel;
            verify BlueDogRequirements::wetJointIntegrity;
        }
        return verdict : VerificationCases::VerdictKind = VerificationCases::VerdictKind::inconclusive;
    }
    verification def <'V-N-045'> WetElectricalIntegrityVerification {
        metadata plannedTest : VerificationCases::VerificationMethod { kind = VerificationCases::VerificationMethodKind::test; }
        doc /* Apply the N-045 qualification conditions. Assess every applicable acceptance outcome separately: N-113, N-114. */
        objective acceptance {
            verify BlueDogRequirements::wetElectricalIntegrity;
            verify BlueDogRequirements::wetConductorResistance;
            verify BlueDogRequirements::wetInsulationResistance;
        }
        return verdict : VerificationCases::VerdictKind = VerificationCases::VerdictKind::inconclusive;
    }
    verification def <'V-N-046'> SolarHeatingVerification {
        metadata plannedTest : VerificationCases::VerificationMethod { kind = VerificationCases::VerificationMethodKind::test; }
        doc /* Apply the N-046 qualification conditions. Assess every applicable acceptance outcome separately: N-115, N-116, N-117. */
        objective acceptance {
            verify BlueDogRequirements::solarHeating;
            verify BlueDogRequirements::hotSunElectronicsOperation;
            verify BlueDogRequirements::hotSunBatteryTemperature;
            verify BlueDogRequirements::batteryChargeTemperatureInhibition;
        }
        return verdict : VerificationCases::VerdictKind = VerificationCases::VerdictKind::inconclusive;
    }
    verification def <'V-N-047'> PrintedMaterialAgingVerification {
        metadata plannedTest : VerificationCases::VerificationMethod { kind = VerificationCases::VerificationMethodKind::test; }
        metadata plannedAnalyze : VerificationCases::VerificationMethod { kind = VerificationCases::VerificationMethodKind::analyze; }
        doc /* Apply the N-047 qualification conditions. Establish aged load-capacity bounds for the production geometry, orientation, material and process under representative exposure. Compare with the capacity credited to each component and verify its demanded loads. Unaged controls characterize degradation; neither an 80-percent ratio nor a fixed coupon count alone establishes qualification. */
        objective acceptance {
            verify BlueDogRequirements::printedMaterialAging;
        }
        return verdict : VerificationCases::VerdictKind = VerificationCases::VerdictKind::inconclusive;
    }
    verification def <'V-N-051'> SelfRightingVerification {
        metadata plannedTest : VerificationCases::VerificationMethod { kind = VerificationCases::VerificationMethodKind::test; }
        doc /* Apply the N-051 qualification conditions. Assess every applicable acceptance outcome separately: N-118, N-119, N-120, N-121. */
        objective acceptance {
            verify BlueDogRequirements::selfRighting;
            verify BlueDogRequirements::rightingDeadline;
            verify BlueDogRequirements::capsizeRigRetention;
            verify BlueDogRequirements::capsizeBallastRetention;
            verify BlueDogRequirements::capsizeElectronicsSealing;
        }
        return verdict : VerificationCases::VerdictKind = VerificationCases::VerdictKind::inconclusive;
    }
    verification def <'V-N-052'> CapsizeControlRecoveryVerification {
        metadata plannedTest : VerificationCases::VerificationMethod { kind = VerificationCases::VerificationMethodKind::test; }
        doc /* Apply the N-052 qualification conditions. Assess every applicable acceptance outcome separately: N-122, N-123, N-124, N-125. */
        objective acceptance {
            verify BlueDogRequirements::capsizeControlRecovery;
            verify BlueDogRequirements::controlRecoveryDeadline;
            verify BlueDogRequirements::capsizeGateProgressRetention;
            verify BlueDogRequirements::capsizeQualificationRetention;
            verify BlueDogRequirements::capsizeRestrictionRetention;
        }
        return verdict : VerificationCases::VerdictKind = VerificationCases::VerdictKind::inconclusive;
    }
    verification def <'V-N-053'> SubmergedWeedPassageVerification {
        metadata plannedTest : VerificationCases::VerificationMethod { kind = VerificationCases::VerificationMethodKind::test; }
        doc /* Apply the N-053 qualification conditions. Assess every applicable acceptance outcome separately: N-126, N-127. */
        objective acceptance {
            verify BlueDogRequirements::submergedWeedPassage;
            verify BlueDogRequirements::weedPassageSpeed;
            verify BlueDogRequirements::weedPassageSteering;
        }
        return verdict : VerificationCases::VerdictKind = VerificationCases::VerdictKind::inconclusive;
    }
    verification def <'V-N-054'> WeedSnagSheddingVerification {
        metadata plannedTest : VerificationCases::VerificationMethod { kind = VerificationCases::VerificationMethodKind::test; }
        doc /* Apply the N-054 qualification conditions. Assess every applicable acceptance outcome separately: N-128, N-129. */
        objective acceptance {
            verify BlueDogRequirements::weedSnagShedding;
            verify BlueDogRequirements::weedSnagSpeedRecovery;
            verify BlueDogRequirements::weedSnagSteeringRecovery;
        }
        return verdict : VerificationCases::VerdictKind = VerificationCases::VerdictKind::inconclusive;
    }
    verification def <'V-N-055'> WeedBlockageResponseVerification {
        metadata plannedTest : VerificationCases::VerificationMethod { kind = VerificationCases::VerificationMethodKind::test; }
        doc /* Apply the N-055 qualification conditions. Assess every applicable acceptance outcome separately: N-130, N-131, N-132, R-101. */
        objective acceptance {
            verify BlueDogRequirements::weedBlockageResponse;
            verify BlueDogRequirements::weedBlockageFault;
            verify BlueDogRequirements::weedBlockageContingency;
            verify BlueDogRequirements::weedBlockageLocation;
            verify BlueDogRequirements::motorQualificationInvariant;
        }
        return verdict : VerificationCases::VerdictKind = VerificationCases::VerdictKind::inconclusive;
    }
    verification def <'V-N-056'> RecoveryPropulsorWeedsVerification {
        metadata plannedTest : VerificationCases::VerificationMethod { kind = VerificationCases::VerificationMethodKind::test; }
        doc /* Apply the N-056 qualification conditions. Assess every applicable acceptance outcome separately: N-133, N-134, N-135, N-136, R-101. */
        objective acceptance {
            verify BlueDogRequirements::recoveryPropulsorWeeds;
            verify BlueDogRequirements::poweredWeedSpeed;
            verify BlueDogRequirements::poweredWeedCurrent;
            verify BlueDogRequirements::poweredWeedTemperature;
            verify BlueDogRequirements::lockedPropulsorShutdown;
            verify BlueDogRequirements::motorQualificationInvariant;
        }
        return verdict : VerificationCases::VerdictKind = VerificationCases::VerdictKind::inconclusive;
    }
    verification def <'V-E-008'> NavigationAvailabilityVerification {
        metadata plannedTest : VerificationCases::VerificationMethod { kind = VerificationCases::VerificationMethodKind::test; }
        doc /* Apply the E-008 qualification conditions. Assess every applicable acceptance outcome separately: E-140, E-141, E-142, E-143, E-132. */
        objective acceptance {
            verify BlueDogRequirements::navigationAvailability;
            verify BlueDogRequirements::navigationValidEpochs;
            verify BlueDogRequirements::staleNavigationInvalidation;
            verify BlueDogRequirements::navigationDegradedTransition;
            verify BlueDogRequirements::staleNavigationUseInhibition;
            verify BlueDogRequirements::criticalEventRecording;
        }
        return verdict : VerificationCases::VerdictKind = VerificationCases::VerdictKind::inconclusive;
    }
    verification def <'V-R-003'> LaunchEnergyAdmissionVerification {
        metadata plannedTest : VerificationCases::VerificationMethod { kind = VerificationCases::VerificationMethodKind::test; }
        doc /* Apply the R-003 qualification conditions. Inject below-reserve, equal-reserve, above-reserve and missing, invalid or stale inputs. */
        objective acceptance {
            verify BlueDogRequirements::launchEnergyAdmission;
        }
        return verdict : VerificationCases::VerdictKind = VerificationCases::VerdictKind::inconclusive;
    }
    verification def <'V-R-004'> ChallengeMotorInhibitionVerification {
        metadata plannedTest : VerificationCases::VerificationMethod { kind = VerificationCases::VerificationMethodKind::test; }
        doc /* Apply the R-004 qualification conditions. Assess every applicable acceptance outcome separately: R-101, R-102, E-138, E-132. */
        objective acceptance {
            verify BlueDogRequirements::challengeMotorInhibition;
            verify BlueDogRequirements::motorQualificationInvariant;
            verify BlueDogRequirements::freshRecoveryCommand;
            verify BlueDogRequirements::qualificationPersistence;
            verify BlueDogRequirements::criticalEventRecording;
        }
        return verdict : VerificationCases::VerdictKind = VerificationCases::VerdictKind::inconclusive;
    }
    verification def <'V-E-201'> SustainedReserveProtectionVerification {
        metadata plannedAnalyze : VerificationCases::VerificationMethod { kind = VerificationCases::VerificationMethodKind::analyze; }
        doc /* Apply the E-201 qualification conditions. For piecewise-constant net power, check the initial state and every interval endpoint. */
        objective acceptance {
            verify BlueDogRequirements::sustainedReserveProtection;
        }
        return verdict : VerificationCases::VerdictKind = VerificationCases::VerdictKind::inconclusive;
    }
    verification def <'V-E-205'> EnergyEvidenceReadinessVerification {
        metadata plannedInspect : VerificationCases::VerificationMethod { kind = VerificationCases::VerificationMethodKind::inspect; }
        metadata plannedAnalyze : VerificationCases::VerificationMethod { kind = VerificationCases::VerificationMethodKind::analyze; }
        doc /* Apply the E-205 qualification conditions to the selected finite or repeating profile. Review configuration-specific installed loads, resources, battery limits, initial energy, reserve route, time resolution, uncertainty, provenance and acceptance disposition. A supplied acceptance Boolean is an input to the predicate, not an automated review of those records. */
        objective acceptance {
            verify BlueDogRequirements::energyEvidenceReadiness;
        }
        return verdict : VerificationCases::VerdictKind = VerificationCases::VerdictKind::inconclusive;
    }
    verification def <'V-L-104'> FailureDispositionVerification {
        metadata plannedInspect : VerificationCases::VerificationMethod { kind = VerificationCases::VerificationMethodKind::inspect; }
        metadata plannedAnalyze : VerificationCases::VerificationMethod { kind = VerificationCases::VerificationMethodKind::analyze; }
        doc /* Review the architecture DFMEA, coverage, accepted mitigations, residual-risk approvals and evidence before launch. The starter list is not complete hazard coverage. */
        objective disposition { verify BlueDogRequirements::criticalFailureDisposition; }
        return verdict : VerificationCases::VerdictKind = VerificationCases::VerdictKind::inconclusive;
    }
    verification def <'V-E-009'> WindObservationVerification {
        metadata plannedTest : VerificationCases::VerificationMethod { kind = VerificationCases::VerificationMethodKind::test; }
        metadata plannedAnalyze : VerificationCases::VerificationMethod { kind = VerificationCases::VerificationMethodKind::analyze; }
        doc /* Run the E-009 installed-flow matrix and fault injections. Record time-correlated reference measurements, delivered observations, validity and control state. Demonstrate E-152 through the M-002 campaign with the same sensor and interface installation. A manufacturer specification alone cannot close installed-error criteria. */
        objective acceptance {
            verify BlueDogRequirements::windObservation;
            verify BlueDogRequirements::windSampleCadence;
            verify BlueDogRequirements::windSpeedAccuracy;
            verify BlueDogRequirements::windDirectionAccuracy;
            verify BlueDogRequirements::windStaleInvalidation;
            verify BlueDogRequirements::invalidWindUseInhibition;
            verify BlueDogRequirements::windLossResponse;
            verify BlueDogRequirements::windSensingEndurance;
        }
        return verdict : VerificationCases::VerdictKind = VerificationCases::VerdictKind::inconclusive;
    }
    verification def <'V-T-107'> StructuralMaterialEvidence {
        metadata plannedTest : VerificationCases::VerificationMethod { kind = VerificationCases::VerificationMethodKind::test; }
        metadata plannedAnalyze : VerificationCases::VerificationMethod { kind = VerificationCases::VerificationMethodKind::analyze; }
        doc /* Establish wet-conditioned, directional production material bounds with documented variability and reductions. Compare every property credited by the released structural analysis with its supported bound. Re-run sizing and load checks after any material/process change. */
        objective acceptance {
            verify BlueDogStructure::wetCouponStrength;
            verify BlueDogStructure::wetCouponStiffness;
        }
        return verdict : VerificationCases::VerdictKind = VerificationCases::VerdictKind::inconclusive;
    }
    verification def <'V-T-102'> FunctionalDeformationEvidence {
        metadata plannedTest : VerificationCases::VerificationMethod { kind = VerificationCases::VerificationMethodKind::test; }
        metadata plannedAnalyze : VerificationCases::VerificationMethod { kind = VerificationCases::VerificationMethodKind::analyze; }
        doc /* Validate member-specific deformation limits against sailing/control, alignment, sealing and clearance functions, then evaluate measured or correlated responses under applicable loads. Provisional numerical percentages cannot set evidence acceptance. */
        objective acceptance {
            verify BlueDogStructure::appendageDeflection;
            verify BlueDogStructure::hullDeflection;
            verify BlueDogStructure::panelDeflection;
        }
        return verdict : VerificationCases::VerdictKind = VerificationCases::VerdictKind::inconclusive;
    }
    verification def <'V-T-101'> StructuralLoadEvidence {
        metadata plannedTest : VerificationCases::VerificationMethod { kind = VerificationCases::VerificationMethodKind::test; }
        metadata plannedAnalyze : VerificationCases::VerificationMethod { kind = VerificationCases::VerificationMethodKind::analyze; }
        doc /* Derive applicable operational, handling and casualty loads from the selected configuration and mission cases. Correlate structural predictions with member, panel, attachment and bond tests. A fixed pressure or tip-force screening probe alone is insufficient. */
        objective acceptance {
            verify BlueDogStructure::structuralIntegrity;
            verify BlueDogStructure::bendingStrength;
            verify BlueDogStructure::panelStrength;
            verify BlueDogStructure::rootProofLoad;
            verify BlueDogStructure::bondProof;
        }
        return verdict : VerificationCases::VerdictKind = VerificationCases::VerdictKind::inconclusive;
    }
    verification def <'V-T-110'> FlotationEvidence {
        metadata plannedTest : VerificationCases::VerificationMethod { kind = VerificationCases::VerificationMethodKind::test; }
        metadata plannedAnalyze : VerificationCases::VerificationMethod { kind = VerificationCases::VerificationMethodKind::analyze; }
        doc /* Assess actual downflooding openings and casualty buoyancy across loading, heel/pitch, wave and ingress cases. Demonstrate flotation through the declared recovery exposure; intact freeboard or volume ratios alone cannot close the case. */
        objective acceptance {
            verify BlueDogStructure::loadedFreeboard;
            verify BlueDogStructure::reserveBuoyancy;
        }
        return verdict : VerificationCases::VerdictKind = VerificationCases::VerdictKind::inconclusive;
    }
    verification def <'V-T-112'> LaunchSiteEvidence {
        metadata plannedTest : VerificationCases::VerificationMethod { kind = VerificationCases::VerificationMethodKind::test; }
        metadata plannedAnalyze : VerificationCases::VerificationMethod { kind = VerificationCases::VerificationMethodKind::analyze; }
        doc /* Record surveyed launch/retrieval paths, depth/stage uncertainty, motion and installed appendage configuration. Check the site-qualified clearance throughout each path. */
        objective acceptance {
            verify BlueDogStructure::launchClearance;
        }
        return verdict : VerificationCases::VerdictKind = VerificationCases::VerdictKind::inconclusive;
    }
    verification def <'V-T-113'> StructuralPrintEnvelope {
        metadata plannedInspect : VerificationCases::VerificationMethod { kind = VerificationCases::VerificationMethodKind::inspect; }
        metadata plannedAnalyze : VerificationCases::VerificationMethod { kind = VerificationCases::VerificationMethodKind::analyze; }
        doc /* Use actual sliced structural jobs including support and printer clearances; test all three positive extents against the owner 250 mm envelope. The study seam/tile dimension is not an acceptance limit. */
        objective acceptance {
            verify BlueDogStructure::printTileEnvelope;
        }
        return verdict : VerificationCases::VerdictKind = VerificationCases::VerdictKind::inconclusive;
    }
    verification def <'V-N-003'> CapsizeResilienceVerification {
        metadata plannedTest : VerificationCases::VerificationMethod { kind = VerificationCases::VerificationMethodKind::test; }
        metadata plannedAnalyze : VerificationCases::VerificationMethod { kind = VerificationCases::VerificationMethodKind::analyze; }
        doc /*
         *  Assess capsize recovery for the declared installed configuration and casualty profile. Use N-051/N-052 only for the selected passive-righting strategy; retain independent C-018 post-capsize shore recovery. Establish required safety capability, restrictions and qualification persistence during inversion and after recovery. A righting result alone cannot close N-003. */
        objective acceptance { verify BlueDogRequirements::capsizeResilience; }
        return verdict : VerificationCases::VerdictKind = VerificationCases::VerdictKind::inconclusive;
    }
    verification def <'V-Q-001'> MissionCapabilityVerification {
        metadata plannedTest : VerificationCases::VerificationMethod { kind = VerificationCases::VerificationMethodKind::test; }
        metadata plannedAnalyze : VerificationCases::VerificationMethod { kind = VerificationCases::VerificationMethodKind::analyze; }
        doc /* For the declared loaded configuration and reproducible route/weather ensemble, establish whole-route sailing capability from accepted sailing, maneuver, energy and recovery evidence. Retain failed routes and holds in exposure accounting. Independently assess preservation of mission-critical functions across the same exposure, including interacting faults and recoveries. Review Q-101 through Q-103 and L-103/L-104 evidence; the provisional L-101/L-102 study target cannot substitute for functional coverage or safety disposition. Numerical screens, a successful isolated course and uncalibrated simulation completion fractions do not close the installed-vessel capability claim. */
        objective acceptance {
            verify BlueDogRequirements::cruisePerformance;
            verify BlueDogRequirements::missionReliability;
        }
        return verdict : VerificationCases::VerdictKind = VerificationCases::VerdictKind::inconclusive;
    }
    verification def <'V-E-203'> PeakSupplyCapabilityVerification {
        metadata plannedTest : VerificationCases::VerificationMethod { kind = VerificationCases::VerificationMethodKind::test; }
        metadata plannedAnalyze : VerificationCases::VerificationMethod { kind = VerificationCases::VerificationMethodKind::analyze; }
        doc /* Measure coincident installed withdrawal demand for each admitted mode and transition, including sensing, signaling, actuation and recovery. Disable harvesting and exercise conservative battery temperature, state of charge, end-of-service capacity, conversion losses and declared uncertainty. Compare each demand with demonstrated supply capability using E-203, and observe voltage-dependent loss of required function and protective trips. A component nameplate or summed nominal power does not establish installed peak delivery. */
        objective acceptance { verify BlueDogRequirements::peakSupplyCapability; }
        return verdict : VerificationCases::VerdictKind = VerificationCases::VerdictKind::inconclusive;
    }
    verification def <'V-T-001'> ConstructionArchitectureVerification {
        metadata plannedInspect : VerificationCases::VerificationMethod { kind = VerificationCases::VerificationMethodKind::inspect; }
        doc /* Inspect the as-built primary shell, bill of materials, manufacturing records and representative sections to establish the owner-selected FDM substrate and wet-layup glass/epoxy construction. Identify configuration, process and departures explicitly. This inspection establishes construction identity only; material, joint, load, durability and flotation acceptance remain separate objectives. */
        objective acceptance { verify BlueDogStructure::hybridConstruction; }
        return verdict : VerificationCases::VerdictKind = VerificationCases::VerdictKind::inconclusive;
    }
    verification def <'V-N-004'> VegetationResilienceVerification {
        metadata plannedTest : VerificationCases::VerificationMethod { kind = VerificationCases::VerificationMethodKind::test; }
        metadata plannedAnalyze : VerificationCases::VerificationMethod { kind = VerificationCases::VerificationMethodKind::analyze; }
        doc /* Apply N-053 through N-056 to the same installed configuration. Assess sailing passage, appendage snag shedding, blockage response and powered recovery separately. Review subsequent control, safety capability and energy use; separate campaign results need a justified combination argument, including compatibility with capsize exposure. */
        objective acceptance { verify BlueDogRequirements::vegetationResilience; }
        return verdict : VerificationCases::VerdictKind = VerificationCases::VerdictKind::inconclusive;
    }

    verification def MissionPerformanceAssessmentVerification {
        metadata plannedAnalyze : VerificationCases::VerificationMethod { kind = VerificationCases::VerificationMethodKind::analyze; }
        doc /* Review the declared reproducible whole-route ensemble and performance evidence for the identified configuration. Include sailing legs, holds, maneuvers and failed routes. Establish input provenance, coverage and limits independently of the provisional reliability targets; a favorable isolated passage is insufficient. */
        objective acceptance {
            verify BlueDogRequirements::legProgress;
            verify BlueDogRequirements::cruiseEvidence;
        }
        return verdict : VerificationCases::VerdictKind = VerificationCases::VerdictKind::inconclusive;
    }
    verification def ReliabilityEvidenceVerification {
        metadata plannedInspect : VerificationCases::VerificationMethod { kind = VerificationCases::VerificationMethodKind::inspect; }
        metadata plannedAnalyze : VerificationCases::VerificationMethod { kind = VerificationCases::VerificationMethodKind::analyze; }
        doc /* Review the configuration-specific mission exposure, critical-function failure-rate bound, confidence method, censoring and observed failures. Assess dependence, common causes and constant-hazard applicability. Accepted rates and a study result do not establish whole-vessel reliability without this argument. */
        objective acceptance { verify BlueDogRequirements::reliabilityEvidence; }
        return verdict : VerificationCases::VerdictKind = VerificationCases::VerdictKind::inconclusive;
    }

}

package BlueDogRecordedEvidence {
    part def CurrentReviewRun :> AnalysisRecords::AnalysisRun {
        attribute :>> caseName default = "BlueDogConfigurationManagement::currentReview";
        attribute scopeCount : ScalarValues::Integer;
        attribute allScopesSameConfiguration : ScalarValues::Boolean;
        attribute installationReconciled : ScalarValues::Boolean;
        attribute resourceEvidenceReady : ScalarValues::Boolean;
        attribute ready : ScalarValues::Boolean;
    }
    part currentReview_run1 : CurrentReviewRun {
        @AnalysisRecords::RecordedRun {
            runAt = "2026-10-23T20:07:50Z";
            tool = "sysml develop-23ca2e2f0";
            command = "%record BlueDogConfigurationManagement::currentReview into BlueDogRecordedEvidence";
            kind = "run";
        }
        attribute :>> caseName = "BlueDogConfigurationManagement::currentReview";
        attribute :>> kind = "run";
        attribute :>> 'objective' = "undecided";
        ref :>> 'subject' = BlueDogConfigurationManagement::ic01;
        attribute :>> subjectName = "BlueDogConfigurationManagement::ic01";
        attribute :>> scopeCount = 7;
        attribute :>> allScopesSameConfiguration = true;
        attribute :>> installationReconciled = false;
        attribute :>> resourceEvidenceReady = false;
        attribute :>> ready = false;
    }
    part def BlueDogSafety_currentReviewRun :> AnalysisRecords::AnalysisRun {
        attribute :>> caseName default = "BlueDogSafety::currentReview";
        attribute hazardCount : ScalarValues::Integer;
        attribute unresolvedHazardCount : ScalarValues::Integer;
        attribute hazardRecordsClosed : ScalarValues::Boolean;
        attribute fmeaReady : ScalarValues::Boolean;
        attribute reviewReady : ScalarValues::Boolean;
        attribute ready : ScalarValues::Boolean;
    }
    part BlueDogSafety_currentReview_run1 : BlueDogSafety_currentReviewRun {
        @AnalysisRecords::RecordedRun {
            runAt = "2026-10-23T20:07:56Z";
            tool = "sysml develop-23ca2e2f0";
            command = "%record BlueDogSafety::currentReview into BlueDogRecordedEvidence";
            kind = "run";
        }
        attribute :>> caseName = "BlueDogSafety::currentReview";
        attribute :>> kind = "run";
        attribute :>> 'objective' = "undecided";
        ref :>> 'subject' = BlueDogSafety::gorge;
        attribute :>> subjectName = "BlueDogSafety::gorge";
        attribute :>> hazardCount = 6;
        attribute :>> unresolvedHazardCount = 6;
        attribute :>> hazardRecordsClosed = false;
        attribute :>> fmeaReady = false;
        attribute :>> reviewReady = false;
        attribute :>> ready = false;
    }
    part def IC01RecoveryIllustrationRun :> AnalysisRecords::AnalysisRun {
        attribute :>> caseName default = "BlueDogIntegratedCandidate::IC01RecoveryIllustration";
        attribute exposureHours : ScalarValues::Real;
        attribute distanceM : ScalarValues::Integer;
        attribute alongCurrentMps : ScalarValues::Real;
        attribute crossCurrentMps : ScalarValues::Integer;
        attribute inverted : ScalarValues::Boolean;
        attribute configurationApplicable : ScalarValues::Boolean;
        attribute configurationId : ScalarValues::String;
        attribute mainNameplateWh : ScalarValues::Integer;
        attribute independentNameplateWh : ScalarValues::Integer;
        attribute remainingWh : ScalarValues::Real;
        attribute groundSpeedMps : ScalarValues::Real;
        attribute transitSeconds : ScalarValues::Real;
        attribute requiredWh : ScalarValues::Real;
        attribute routeFeasible : ScalarValues::Boolean;
        attribute reserveFits : ScalarValues::Boolean;
        attribute physicalQualification : ScalarValues::Boolean;
    }
    part IC01RecoveryIllustration_run1 : IC01RecoveryIllustrationRun {
        @AnalysisRecords::RecordedRun {
            runAt = "2026-10-23T20:07:58Z";
            tool = "sysml develop-23ca2e2f0";
            command = "%record BlueDogIntegratedCandidate::IC01RecoveryIllustration into BlueDogRecordedEvidence";
            kind = "run";
        }
        attribute :>> caseName = "BlueDogIntegratedCandidate::IC01RecoveryIllustration";
        attribute :>> kind = "run";
        attribute :>> 'objective' = "undecided";
        ref :>> 'subject' = BlueDogIC01::design;
        attribute :>> subjectName = "BlueDogIC01::design";
        attribute :>> exposureHours = 4.0;
        attribute :>> distanceM = 600;
        attribute :>> alongCurrentMps = -0.4;
        attribute :>> crossCurrentMps = 0;
        attribute :>> inverted = false;
        attribute :>> configurationApplicable = true;
        attribute :>> configurationId = "IC-01";
        attribute :>> mainNameplateWh = 1300;
        attribute :>> independentNameplateWh = 60;
        attribute :>> remainingWh = 43.0;
        attribute :>> groundSpeedMps = 1.1;
        attribute :>> transitSeconds = 545.4545454545454;
        attribute :>> requiredWh = 12.545454545454543;
        attribute :>> routeFeasible = true;
        attribute :>> reserveFits = true;
        attribute :>> physicalQualification = false;
        part verdict1 : AnalysisRecords::VerdictRecord :> verdicts {
            attribute :>> kind = "assertion";
            attribute :>> name = "configurationApplicability";
            attribute :>> status = "satisfied";
        }
        part verdict2 : AnalysisRecords::VerdictRecord :> verdicts {
            attribute :>> kind = "assertion";
            attribute :>> name = "inputDomain";
            attribute :>> status = "satisfied";
        }
    }
}

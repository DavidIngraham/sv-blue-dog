package InlandExtended {
 private import ScalarValues::*;
 enum def Truth { yes; no; unknown; }
 enum def Mode { sail; power; rowing; towingAstern; pushing; towed; pushed; trawling; fishing; nuc; ram; dredging; diving; mineClearance; pilot; seaplane; wig; airCushion; mooredBarge; }
 enum def Side { portSide; starboardSide; ahead; aft; unresolved; }
 part context;
 analysis def General {
  doc /* Rules 1-8. Candidate-action and evidence checks, not a sensor estimator or safe-speed optimizer. Judgment inputs require external evidence; no universal CPA/time/turn threshold is invented. Rule 4 applies general duties in all visibility. Rule 3 definitions are externally classified facts. Rule 2 departure requires assessed necessity, never a blanket emergency exemption.*/
  subject encounter;
  in attribute factsKnown : Boolean;
  in attribute inlandWaters : Boolean;
  in attribute jurisdictionReviewed : Boolean;
  in attribute localProvisionsSatisfied : Boolean;
  in attribute visualLookout : Boolean;
  in attribute hearingLookout : Boolean;
  in attribute appropriateMeansUsed : Boolean;
  in attribute radarOperational : Boolean;
  in attribute radarLongRangeUsed : Boolean;
  in attribute radarPlottingUsed : Boolean;
  in attribute visibilityReviewed : Boolean;
  in attribute trafficDensityReviewed : Boolean;
  in attribute maneuverabilityReviewed : Boolean;
  in attribute backgroundLightsReviewed : Boolean;
  in attribute weatherCurrentReviewed : Boolean;
  in attribute draftDepthReviewed : Boolean;
  in attribute radarLimitsReviewed : Boolean;
  in attribute positiveAction : Boolean;
  in attribute earlyAction : Boolean;
  in attribute substantialAction : Boolean;
  in attribute noNewCloseQuarters : Boolean;
  in attribute safePassingDistance : Boolean;
  in attribute effectivenessMonitored : Boolean;
  in attribute finallyClear : Boolean;
  in attribute speedReductionNecessary : Boolean;
  in attribute speedReduced : Boolean;
  in attribute immediateDanger : Boolean;
  in attribute departureNecessary : Boolean;
  in attribute departureLimitedToNecessity : Boolean;
  in attribute specialCircumstancesReviewed : Boolean;
  in attribute riskAssessment : InlandExtended::Truth;
  in attribute approaching : Boolean;
  in attribute bearingSteady : Boolean;
  in attribute largeTowOrCloseRange : Boolean;
  in attribute otherRiskEvidence : Boolean;
  out attribute rule1Applicable : Boolean = inlandWaters;
  out attribute rule2DepartureAssessmentSupported : Boolean = factsKnown and immediateDanger and departureNecessary and departureLimitedToNecessity and specialCircumstancesReviewed;
  out attribute rule5Supported : Boolean = factsKnown and visualLookout and hearingLookout and appropriateMeansUsed;
  out attribute rule6Supported : Boolean = factsKnown and visibilityReviewed and trafficDensityReviewed and maneuverabilityReviewed and backgroundLightsReviewed and weatherCurrentReviewed and draftDepthReviewed and (not radarOperational or radarLimitsReviewed);
  out attribute rule7RiskPresent : Boolean = riskAssessment != Truth::no or (approaching and bearingSteady) or otherRiskEvidence;
  out attribute rule7FurtherAppraisalRequired : Boolean = not factsKnown or (largeTowOrCloseRange and approaching) or (radarOperational and (not radarLongRangeUsed or not radarPlottingUsed));
  out attribute rule8MonitorRequired : Boolean = not finallyClear;
  out attribute rule8CandidateSupported : Boolean = factsKnown and positiveAction and earlyAction and substantialAction and noNewCloseQuarters and safePassingDistance and (finallyClear or effectivenessMonitored) and (not speedReductionNecessary or speedReduced);
  out attribute assessmentSupported : Boolean = inlandWaters and jurisdictionReviewed and localProvisionsSatisfied and rule5Supported and rule6Supported and not rule7FurtherAppraisalRequired and rule8CandidateSupported;
  out attribute completeComplianceEstablished : Boolean = false;
 }
 analysis def ChannelsAndTSS {
  doc /* Rules 8(f), 9 and 10. River encounter priority is in Assess; signal exchanges are in Signals. A necessary maintenance/cable exemption is a supplied, clause-limited determination: tssSupported is not overall compliance, and exemptionScopeReviewRequired remains true. Facts about legally designated schemes and geography require authoritative review.*/
  subject encounter;
  in attribute factsKnown : Boolean;
  in attribute channel : Boolean;
  in attribute ownSailing : Boolean;
  in attribute ownFishing : Boolean;
  in attribute otherConfined : Boolean;
  in attribute otherNavigatingChannel : Boolean;
  in attribute crossingChannel : Boolean;
  in attribute crossingImpede : Boolean;
  in attribute followingChannel : Boolean;
  in attribute safePracticableStarboardEdge : Boolean;
  in attribute nearObscuredBend : Boolean;
  in attribute caution : Boolean;
  in attribute bendSignal : Boolean;
  in attribute anchors : Boolean;
  in attribute avoidAnchoringPracticable : Boolean;
  in attribute tss : Boolean;
  in attribute usesLane : Boolean;
  in attribute followsFlow : Boolean;
  in attribute clearSeparation : Boolean;
  in attribute joinsLeaves : Boolean;
  in attribute atTermination : Boolean;
  in attribute smallJoinAngle : Boolean;
  in attribute crossesLane : Boolean;
  in attribute crossingAvoidable : Boolean;
  in attribute rightAngleHeading : Boolean;
  in attribute usesInshore : Boolean;
  in attribute canUseLane : Boolean;
  in attribute destinationException : Boolean;
  in attribute immediateDanger : Boolean;
  in attribute entersSeparationZone : Boolean;
  in attribute fishingInZone : Boolean;
  in attribute necessaryMaintenanceExemption : Boolean;
  in attribute necessaryCableExemption : Boolean;
  in attribute nearTermination : Boolean;
  in attribute terminationCaution : Boolean;
  in attribute wideAvoidanceMargin : Boolean;
  in attribute otherFollowingLane : Boolean;
  in attribute otherPower : Boolean;
  in attribute earlySeaRoom : Boolean;
  in attribute providedNonImpediment : Boolean;
  in attribute lengthM : Real;
  out attribute channelNonImpediment : Boolean = channel and (((ownSailing or lengthM < 20) and otherConfined) or (ownFishing and otherNavigatingChannel) or (crossingChannel and otherConfined));
  out attribute channelCrossingProhibited : Boolean = channel and crossingChannel and otherConfined and crossingImpede;
  out attribute channelBendSignalRequired : Boolean = channel and nearObscuredBend;
  out attribute channelAvoidAnchor : Boolean = channel and anchors and avoidAnchoringPracticable;
  out attribute channelSupported : Boolean = factsKnown and lengthM > 0 and not channelCrossingProhibited and not channelAvoidAnchor and (not (channel and followingChannel) or safePracticableStarboardEdge) and (not channelBendSignalRequired or (caution and bendSignal)) and (not channelNonImpediment or (earlySeaRoom and providedNonImpediment));
  out attribute limitedTssExemption : Boolean = necessaryMaintenanceExemption or necessaryCableExemption;
  out attribute inshorePermitted : Boolean = lengthM < 20 or ownSailing or ownFishing or not canUseLane or destinationException or immediateDanger;
  out attribute separationEntryPermitted : Boolean = crossesLane or joinsLeaves or immediateDanger or fishingInZone;
  out attribute tssNonImpediment : Boolean = tss and otherFollowingLane and (ownFishing or ((lengthM < 20 or ownSailing) and otherPower));
  out attribute ordinaryTssGeometrySupported : Boolean = (not usesLane or (followsFlow and clearSeparation and (not joinsLeaves or atTermination or smallJoinAngle))) and (not crossesLane or (not crossingAvoidable and rightAngleHeading)) and (not usesInshore or inshorePermitted) and (not entersSeparationZone or separationEntryPermitted) and (not nearTermination or terminationCaution) and (not anchors or not avoidAnchoringPracticable) and (usesLane or wideAvoidanceMargin);
  out attribute tssSupported : Boolean = factsKnown and lengthM > 0 and (not tss or ((ordinaryTssGeometrySupported or limitedTssExemption) and (not tssNonImpediment or (earlySeaRoom and providedNonImpediment))));
  out attribute exemptionScopeReviewRequired : Boolean = tss and limitedTssExemption;
  out attribute completeComplianceEstablished : Boolean = false;
 }
 analysis def RestrictedVisibility {
  doc /* Rule 19; no stand-on assignment is produced. Candidate restrictions use assessed relative geometry, radar-only acquisition and risk. Port/toward-target avoidance is treated conservatively without an automatic exception; any necessary departure needs separate Rule 2 assessment.*/
  subject encounter;
  in attribute factsKnown : Boolean;
  in attribute inSight : Boolean;
  in attribute inOrNearRestricted : Boolean;
  in attribute radarOnly : Boolean;
  in attribute forwardOfBeam : Boolean;
  in attribute abeamOrAbaft : Boolean;
  in attribute ownOvertaking : Boolean;
  in attribute portTurn : Boolean;
  in attribute towardTargetTurn : Boolean;
  in attribute courseAlteration : Boolean;
  in attribute closeQuarters : Boolean;
  in attribute fogSignalForward : Boolean;
  in attribute cannotAvoidForwardClose : Boolean;
  in attribute minimumSteerageSpeed : Boolean;
  in attribute allWayOffNecessary : Boolean;
  in attribute allWayOff : Boolean;
  in attribute extremeCaution : Boolean;
  in attribute enginePowered : Boolean;
  in attribute enginesReady : Boolean;
  in attribute earlyAvoidance : Boolean;
  in attribute safeSpeedAdapted : Boolean;
  in attribute risk : InlandExtended::Truth;
  out attribute applicable : Boolean = not inSight and inOrNearRestricted;
  out attribute avoidanceRequired : Boolean = applicable and radarOnly and (risk != Truth::no or closeQuarters);
  out attribute avoidPortTurn : Boolean = avoidanceRequired and courseAlteration and forwardOfBeam and not ownOvertaking;
  out attribute avoidTowardTarget : Boolean = avoidanceRequired and courseAlteration and abeamOrAbaft;
  out attribute minimumSpeedRequired : Boolean = applicable and risk != Truth::no and (fogSignalForward or cannotAvoidForwardClose);
  out attribute engineReadinessRequired : Boolean = applicable and enginePowered;
  out attribute candidateSupported : Boolean = factsKnown and (not applicable or (safeSpeedAdapted and (not engineReadinessRequired or enginesReady) and (not avoidanceRequired or earlyAvoidance) and (not avoidPortTurn or not portTurn) and (not avoidTowardTarget or not towardTargetTurn) and (not minimumSpeedRequired or (minimumSteerageSpeed and extremeCaution and (not allWayOffNecessary or allWayOff)))));
  out attribute completeComplianceEstablished : Boolean = false;
 }
 analysis def LightsAndShapes {
  doc /* Rules 20-31. Pattern obligations and size boundaries, not automatic image recognition. Outputs are simultaneous: ordinary/status/anchor/tow supplements must be combined by applicability. Specialized group tow layouts, fishing optional signals and approved alternatives are assessed separately. Rule 28 is reserved in Inland Rules; no constrained-by-draft privilege is invented.*/
  subject encounter;
  in attribute factsKnown : Boolean;
  in attribute night : Boolean;
  in attribute restrictedVisibility : Boolean;
  in attribute lightsCarried : Boolean;
  in attribute lightsDeemedNecessary : Boolean;
  in attribute makingWay : Boolean;
  in attribute underway : Boolean;
  in attribute anchored : Boolean;
  in attribute aground : Boolean;
  in attribute specialAnchorage : Boolean;
  in attribute awayFromNavigation : Boolean;
  in attribute sailAlsoPowered : Boolean;
  in attribute normalSailLightsPracticable : Boolean;
  in attribute chooseSmallSailAlternative : Boolean;
  in attribute chooseSmallPowerAlternative : Boolean;
  in attribute chooseSmallStatusExemption : Boolean;
  in attribute compositeUnit : Boolean;
  in attribute gearBeyond150m : Boolean;
  in attribute divingSmallDisplay : Boolean;
  in attribute obstruction : Boolean;
  in attribute gearRestrictedTowing : Boolean;
  in attribute partiallySubmerged : Boolean;
  in attribute towLightingImpracticable : Boolean;
  in attribute assistanceTow : Boolean;
  in attribute airActivity : Boolean;
  in attribute nonDisplacement : Boolean;
  in attribute mooredProjectsIntoChannel : Boolean;
  in attribute mooredWidthBelow80 : Boolean;
  in attribute groupMoreThanTwoWide : Boolean;
  in attribute groupWidthOver25 : Boolean;
  in attribute mooredParallel : Boolean;
  in attribute shelteredBargeExemption : Boolean;
  in attribute geographicBargeExemption : Boolean;
  in attribute allRequiredDisplaysPresent : Boolean;
  in attribute annexInstallationAccepted : Boolean;
  in attribute otherLightsNonConfusing : Boolean;
  in attribute mode : InlandExtended::Mode;
  in attribute lengthM : Real;
  in attribute towLengthM : Real;
  in attribute towBreadthM : Real;
  in attribute objectLengthM : Real;
  out attribute valid : Boolean = factsKnown and lengthM > 0 and towLengthM >= 0 and towBreadthM >= 0 and objectLengthM >= 0 and not (anchored and aground);
  out attribute displayLights : Boolean = night or (restrictedVisibility and lightsCarried) or lightsDeemedNecessary;
  out attribute displayShapes : Boolean = not night;
  out attribute smallSailAlternative : Boolean = not sailAlsoPowered and (mode == Mode::rowing or (mode == Mode::sail and lengthM < 7 and not normalSailLightsPracticable and chooseSmallSailAlternative));
  out attribute smallPowerAlternative : Boolean = (mode == Mode::power or sailAlsoPowered) and lengthM < 12 and chooseSmallPowerAlternative;
  out attribute smallStatusExemption : Boolean = lengthM < 12 and chooseSmallStatusExemption and mode != Mode::diving;
  out attribute anchorExemption : Boolean = anchored and ((lengthM < 7 and awayFromNavigation) or (lengthM < 20 and specialAnchorage));
  out attribute bargeLightsRequired : Boolean = mode == Mode::mooredBarge and not shelteredBargeExemption and not geographicBargeExemption and not (lengthM < 20 and specialAnchorage) and (mooredProjectsIntoChannel or mooredWidthBelow80 or groupMoreThanTwoWide or groupWidthOver25 or not mooredParallel);
  out attribute ordinaryUnderwayPattern : String = if smallSailAlternative ? "All-round white OR white torch/lantern displayed in time to prevent collision" else if (mode == Mode::sail or mode == Mode::rowing) and not sailAlsoPowered ? "Sidelights and sternlight; under 20 m combined masthead lantern is an option" else if smallPowerAlternative ? "All-round white and sidelights" else if lengthM >= 50 ? "Two masthead lights, sidelights and sternlight" else "Forward masthead, sidelights and sternlight";
  out attribute statusPattern : String = if mode == Mode::trawling ? "Green over white; two cones apexes together; aft higher masthead required at 50 m or more; sidelights/sternlight when making way" else if mode == Mode::fishing ? "Red over white; two cones apexes together; sidelights/sternlight when making way" else if mode == Mode::nuc ? (if smallStatusExemption ? "Rule 27 small-vessel display exemption selected" else "Two red all-round lights; two balls; sidelights/sternlight when making way") else if mode == Mode::ram or mode == Mode::dredging ? (if smallStatusExemption ? "Rule 27 small-vessel display exemption selected" else "Red-white-red all-round; ball-diamond-ball; power underway lights when making way") else if mode == Mode::diving ? (if divingSmallDisplay ? "Red-white-red all-round and rigid code flag A at least 1 m; all-round flag visibility" else "RAM display plus obstruction/passable-side displays when applicable") else if mode == Mode::mineClearance ? (if smallStatusExemption ? "Rule 27 small-vessel display exemption selected" else "Three green all-round lights or three balls in prescribed arrangement; dangerous within 1000 m") else if mode == Mode::pilot ? "White over red; sidelights/sternlight underway; anchor display at anchor" else "No additional status pattern";
  out attribute anchorPattern : String = if mode == Mode::fishing or mode == Mode::trawling ? "Rule 26 fishing display instead of anchor display" else if anchorExemption ? "Anchor display exemption applies" else if anchored or aground ? (if lengthM < 50 ? "One all-round white; anchor ball by day" else "Forward all-round white and lower aft white; anchor ball by day") else "No anchor display";
  out attribute groundingExtraRequired : Boolean = aground and lengthM >= 12;
  out attribute groundingExtraPattern : String = "If practicable: two red all-round lights and three balls";
  out attribute anchorDeckIlluminationRequired : Boolean = anchored and lengthM >= 100;
  out attribute sailMotorConeRequired : Boolean = sailAlsoPowered and lengthM >= 12;
  out attribute outlyingGearDisplayRequired : Boolean = mode == Mode::fishing and gearBeyond150m;
  out attribute outlyingGearPattern : String = "White all-round or cone apex upward toward gear";
  out attribute obstructionDisplayRequired : Boolean = (mode == Mode::dredging or mode == Mode::diving) and obstruction and not smallStatusExemption and not divingSmallDisplay;
  out attribute obstructionPattern : String = "Obstructed side: two red lights/two balls; passable side: two green lights/two diamonds; at anchor use these instead of Rule 30";
  out attribute airSupplement : String = if mode == Mode::airCushion and nonDisplacement ? "All-round flashing yellow" else if mode == Mode::wig and airActivity ? "High-intensity all-round flashing red" else "None";
  out attribute rule31ClosestPossibleRequired : Boolean = (mode == Mode::seaplane or mode == Mode::wig) and not allRequiredDisplaysPresent;
  out attribute rule28Reserved : Boolean = true;
  out attribute mastheadTowStackCount : Integer = if compositeUnit ? 0 else if mode == Mode::towingAstern ? (if towLengthM > 200 ? 3 else 2) else if mode == Mode::pushing ? 2 else 0;
  out attribute longTowDiamondRequired : Boolean = not compositeUnit and towLengthM > 200 and (mode == Mode::towingAstern or mode == Mode::towed);
  out attribute towPattern : String = if compositeUnit ? "Rule 23 power-driven composite unit" else if mode == Mode::towingAstern ? "Vertical masthead stack, sidelights, sternlight, yellow towing light above sternlight; Rule 23 masthead positioning applies" else if mode == Mode::pushing ? "Two masthead lights, sidelights, two towing lights; applicable river alternative requires review" else if mode == Mode::pushed ? "Forward sidelights and special flashing light" else if mode == Mode::towed and partiallySubmerged ? "White all-round outline lights and aft diamond" else if mode == Mode::towed ? "Sidelights and sternlight; alongside/group arrangements require review" else "No tow pattern";
  out attribute partialTowOutlineLightMinimum : Integer = if not partiallySubmerged ? 0 else if towBreadthM < 25 ? 2 else 4;
  out attribute partialTowIntermediateLightsRequired : Boolean = partiallySubmerged and objectLengthM > 100;
  out attribute partialTowMaxLightSpacingM : Real = 100;
  out attribute practicabilityAlternativeReviewRequired : Boolean = towLightingImpracticable or assistanceTow or rule31ClosestPossibleRequired;
  out attribute displayEvidenceSupported : Boolean = valid and allRequiredDisplaysPresent and annexInstallationAccepted and otherLightsNonConfusing and not practicabilityAlternativeReviewRequired;
  out attribute completeComplianceEstablished : Boolean = false;
  out attribute restrictedTowRamDisplayRequired : Boolean = gearRestrictedTowing and not smallStatusExemption;
  out attribute restrictedTowRamPattern : String = "In addition to Rule 24: red-white-red all-round and ball-diamond-ball";
 }
 analysis def Signals {
  doc /* Rules 32-37. Inland signal meanings differ from International maneuver signals. shortToleranceS is an explicit engineering interpretation of about one second. Signals are obligations/due events, not proof they were emitted or heard. Radio agreement removes only applicable passage-whistle duties, not danger/fog signals. Distress selection must be an authorized Annex IV signal; no transmitter is actuated.*/
  subject encounter;
  in attribute factsKnown : Boolean;
  in attribute inSight : Boolean;
  in attribute approaching : Boolean;
  in attribute powerPair : Boolean;
  in attribute underway : Boolean;
  in attribute meetingCrossing : Boolean;
  in attribute withinHalfMile : Boolean;
  in attribute overtaking : Boolean;
  in attribute intendLeaveOnPort : Boolean;
  in attribute intendOvertakeStarboard : Boolean;
  in attribute asternPropulsion : Boolean;
  in attribute passingAgreementReached : Boolean;
  in attribute otherProposalHeard : Boolean;
  in attribute proposalAccepted : Boolean;
  in attribute doubt : Boolean;
  in attribute bendOrObstruction : Boolean;
  in attribute heardBendSignal : Boolean;
  in attribute leavingBerth : Boolean;
  in attribute restrictedVisibility : Boolean;
  in attribute makingWay : Boolean;
  in attribute anchored : Boolean;
  in attribute aground : Boolean;
  in attribute mannedLastTow : Boolean;
  in attribute compositeUnit : Boolean;
  in attribute chooseSmallEfficientAlternative : Boolean;
  in attribute efficientSoundAvailable : Boolean;
  in attribute specialAnchorage : Boolean;
  in attribute pilotDuty : Boolean;
  in attribute distress : Boolean;
  in attribute assistanceRequired : Boolean;
  in attribute distressSignalChosen : Boolean;
  in attribute attentionNeeded : Boolean;
  in attribute attentionSignalNonConfusing : Boolean;
  in attribute attentionDoesNotDazzle : Boolean;
  in attribute signalEquipmentAccepted : Boolean;
  in attribute mode : InlandExtended::Mode;
  in attribute lengthM : Real;
  in attribute elapsedFogSignalS : Real;
  in attribute shortBlastS : Real;
  in attribute shortToleranceS : Real;
  in attribute prolongedBlastS : Real;
  out attribute whistleRequired : Boolean = lengthM >= 12;
  out attribute bellRequired : Boolean = lengthM >= 20;
  out attribute gongRequired : Boolean = lengthM >= 100;
  out attribute efficientSoundRequired : Boolean = lengthM < 12;
  out attribute blastDurationsSupported : Boolean = shortToleranceS >= 0 and shortBlastS >= 1-shortToleranceS and shortBlastS <= 1+shortToleranceS and prolongedBlastS >= 4 and prolongedBlastS <= 6;
  out attribute dangerSignalRequired : Boolean = inSight and approaching and doubt;
  out attribute dangerMinimumShortBlasts : Integer = if dangerSignalRequired ? 5 else 0;
  out attribute maneuverSignalRequired : Boolean = inSight and powerPair and underway and ((meetingCrossing and withinHalfMile) or overtaking) and not passingAgreementReached;
  out attribute maneuverShortBlasts : Integer = if not maneuverSignalRequired ? 0 else if asternPropulsion ? 3 else if overtaking ? (if intendOvertakeStarboard ? 1 else 2) else if intendLeaveOnPort ? 1 else 2;
  out attribute answerSameSignalRequired : Boolean = inSight and powerPair and otherProposalHeard and proposalAccepted and not passingAgreementReached;
  out attribute precautionUntilAgreementRequired : Boolean = inSight and powerPair and otherProposalHeard and not proposalAccepted;
  out attribute prolongedBendSignalRequired : Boolean = bendOrObstruction or heardBendSignal;
  out attribute prolongedDepartureSignalRequired : Boolean = leavingBerth and mode == Mode::power;
  out attribute smallFogAlternative : Boolean = chooseSmallEfficientAlternative and (lengthM < 12 or (lengthM < 20 and (anchored or aground)));
  out attribute fogAnchorExemption : Boolean = anchored and not aground and specialAnchorage and lengthM < 20 and mode != Mode::fishing and mode != Mode::trawling and not legallyRam;
  out attribute fogPattern : String = if not restrictedVisibility ? "None" else if fogAnchorExemption ? "Special anchorage exemption" else if smallFogAlternative ? "Other efficient sound" else if legallyRam or mode == Mode::fishing or mode == Mode::trawling ? "One prolonged then two short" else if aground ? "Anchor bell pattern plus three distinct strokes before and after; gong at 100 m" else if anchored ? "Rapid bell about 5 s; gong about 5 s after bell at 100 m" else if compositeUnit or mode == Mode::power or mode == Mode::pilot or mode == Mode::seaplane or mode == Mode::wig or mode == Mode::airCushion ? (if makingWay ? "One prolonged" else "Two prolonged separated by about 2 s") else if mode == Mode::towed and mannedLastTow ? "One prolonged then three short, after tug when practicable" else if mode == Mode::towed ? "No manned-tow signal duty" else "One prolonged then two short";
  out attribute fogSignalIntervalMaxS : Real = if not restrictedVisibility or fogAnchorExemption or (mode == Mode::towed and not mannedLastTow) ? 0 else if not smallFogAlternative and (anchored or aground) and not legallyRam and mode != Mode::fishing and mode != Mode::trawling ? 60 else 120;
  out attribute fogSignalDue : Boolean = fogSignalIntervalMaxS > 0 and elapsedFogSignalS >= fogSignalIntervalMaxS;
  out attribute pilotIdentityOptionalBlasts : Integer = if pilotDuty ? 4 else 0;
  out attribute distressSignalRequired : Boolean = distress and assistanceRequired;
  out attribute distressSignalMisuse : Boolean = distressSignalChosen and not distressSignalRequired;
  out attribute attentionSignalPermitted : Boolean = attentionNeeded and attentionSignalNonConfusing and attentionDoesNotDazzle;
  out attribute candidateSupported : Boolean = factsKnown and lengthM > 0 and elapsedFogSignalS >= 0 and blastDurationsSupported and signalEquipmentAccepted and (not efficientSoundRequired or efficientSoundAvailable) and (not smallFogAlternative or efficientSoundAvailable) and not distressSignalMisuse and (not distressSignalRequired or distressSignalChosen) and (not attentionNeeded or attentionSignalPermitted);
  out attribute completeComplianceEstablished : Boolean = false;
  out attribute legallyRam : Boolean = mode == Mode::ram or mode == Mode::dredging or mode == Mode::diving;
 }
 enum def LightKind {
     enum masthead;
     enum portSide;
     enum starboardSide;
     enum stern;
     enum towing;
     enum allRoundWhite;
     enum allRoundRed;
     enum allRoundGreen;
     enum specialFlashing;
     enum flashingYellow;
     enum flashingRed;
 }
 enum def Color {
     enum white;
     enum red;
     enum green;
     enum yellow;
 }
 analysis def LightFixture {
  doc /* Rules 21/22 and selected Annex I numerical demands. Color region checks are screening only; optical certification/evidence remains required. Red corner coordinates are ordered around their convex boundary, not read as a self-crossing polygon in table-column order. White uses the stated boundary order. This interpretation requires review against the incorporated CIE standard. Units: m, degrees, nautical miles, candela, flashes/minute.*/
  subject encounter;
  in attribute kind : InlandExtended::LightKind;
  in attribute lengthM : Real;
  in attribute nominalArcDeg : Real;
  in attribute measuredRangeNm : Real;
  in attribute minimumMeasuredIntensityCd : Real;
  in attribute colorX : Real;
  in attribute colorY : Real;
  in attribute flashesPerMinute : Real;
  in attribute factsKnown : Boolean;
  in attribute submergedTow : Boolean;
  in attribute unmannedBarge : Boolean;
  in attribute sailingUnderway : Boolean;
  in attribute horizontalSectorEvidenceAccepted : Boolean;
  in attribute verticalSectorEvidenceAccepted : Boolean;
  in attribute installationPositionEvidenceAccepted : Boolean;
  in attribute screensEvidenceAccepted : Boolean;
  out attribute requiredRangeNm : Real = if submergedTow ? 3 else if kind == LightKind::specialFlashing ? 2 else if kind == LightKind::masthead ? (if lengthM >= 50 ? 6 else if lengthM >= 20 ? 5 else if lengthM >= 12 ? 3 else 2) else if kind == LightKind::portSide or kind == LightKind::starboardSide ? (if lengthM >= 50 ? 3 else if lengthM >= 12 ? 2 else 1) else if lengthM >= 50 ? 3 else 2;
  out attribute requiredArcMinDeg : Real = if kind == LightKind::masthead ? 225 else if kind == LightKind::portSide or kind == LightKind::starboardSide ? 112.5 else if kind == LightKind::stern or kind == LightKind::towing ? 135 else if kind == LightKind::specialFlashing ? 180 else 360;
  out attribute requiredArcMaxDeg : Real = if kind == LightKind::specialFlashing ? 225 else requiredArcMinDeg;
  out attribute requiredColor : InlandExtended::Color = if kind == LightKind::portSide or kind == LightKind::allRoundRed or kind == LightKind::flashingRed ? Color::red else if kind == LightKind::starboardSide or kind == LightKind::allRoundGreen ? Color::green else if kind == LightKind::towing or kind == LightKind::specialFlashing or kind == LightKind::flashingYellow ? Color::yellow else Color::white;
  out attribute minimumIntensityCd : Real = if requiredRangeNm == 1 ? 0.686/0.8 else if requiredRangeNm == 2 ? 0.686*4/(0.8*0.8) else if requiredRangeNm == 3 ? 0.686*9/(0.8*0.8*0.8) else if requiredRangeNm == 5 ? 0.686*25/(0.8*0.8*0.8*0.8*0.8) else 0.686*36/(0.8*0.8*0.8*0.8*0.8*0.8);
  out attribute requiredVerticalOuterDeg : Real = if unmannedBarge ? 0 else if sailingUnderway ? 25 else 7.5;
  out attribute requiredOuterIntensityFraction : Real = if unmannedBarge ? 1 else if sailingUnderway ? 0.5 else 0.6;
  out attribute flashSupported : Boolean = if kind == LightKind::specialFlashing ? flashesPerMinute >= 50 and flashesPerMinute <= 70 else if kind == LightKind::flashingRed or kind == LightKind::flashingYellow ? flashesPerMinute >= 120 else true;
  out attribute whiteChromaticity : Boolean = (((((((0.382 > colorY) != (0.44 > colorY)) and colorX < (0.000000000)*(colorY-0.382)/(0.058000000)+0.525) != (((0.44 > colorY) != (0.348 > colorY)) and colorX < (-0.142000000)*(colorY-0.44)/(-0.092000000)+0.452)) != (((0.348 > colorY) != (0.283 > colorY)) and colorX < (0.000000000)*(colorY-0.348)/(-0.065000000)+0.31)) != (((0.283 > colorY) != (0.382 > colorY)) and colorX < (0.133000000)*(colorY-0.283)/(0.099000000)+0.31))) or (((0.000000000)*(colorY-0.382)-(0.058000000)*(colorX-0.525)) == 0 and colorX >= 0.525 and colorX <= 0.525 and colorY >= 0.382 and colorY <= 0.44) or (((-0.073000000)*(colorY-0.44)-(0.000000000)*(colorX-0.525)) == 0 and colorX >= 0.452 and colorX <= 0.525 and colorY >= 0.44 and colorY <= 0.44) or (((-0.142000000)*(colorY-0.44)-(-0.092000000)*(colorX-0.452)) == 0 and colorX >= 0.31 and colorX <= 0.452 and colorY >= 0.348 and colorY <= 0.44) or (((0.000000000)*(colorY-0.348)-(-0.065000000)*(colorX-0.31)) == 0 and colorX >= 0.31 and colorX <= 0.31 and colorY >= 0.283 and colorY <= 0.348) or (((0.133000000)*(colorY-0.283)-(0.099000000)*(colorX-0.31)) == 0 and colorX >= 0.31 and colorX <= 0.443 and colorY >= 0.283 and colorY <= 0.382) or (((0.082000000)*(colorY-0.382)-(0.000000000)*(colorX-0.443)) == 0 and colorX >= 0.443 and colorX <= 0.525 and colorY >= 0.382 and colorY <= 0.382);
  out attribute greenChromaticity : Boolean = (((((((0.385 > colorY) != (0.723 > colorY)) and colorX < (-0.019000000)*(colorY-0.385)/(0.338000000)+0.028) != (((0.723 > colorY) != (0.511 > colorY)) and colorX < (0.291000000)*(colorY-0.723)/(-0.212000000)+0.009)) != (((0.511 > colorY) != (0.356 > colorY)) and colorX < (-0.097000000)*(colorY-0.511)/(-0.155000000)+0.3)) != (((0.356 > colorY) != (0.385 > colorY)) and colorX < (-0.175000000)*(colorY-0.356)/(0.029000000)+0.203))) or (((-0.019000000)*(colorY-0.385)-(0.338000000)*(colorX-0.028)) == 0 and colorX >= 0.009 and colorX <= 0.028 and colorY >= 0.385 and colorY <= 0.723) or (((0.291000000)*(colorY-0.723)-(-0.212000000)*(colorX-0.009)) == 0 and colorX >= 0.009 and colorX <= 0.3 and colorY >= 0.511 and colorY <= 0.723) or (((-0.097000000)*(colorY-0.511)-(-0.155000000)*(colorX-0.3)) == 0 and colorX >= 0.203 and colorX <= 0.3 and colorY >= 0.356 and colorY <= 0.511) or (((-0.175000000)*(colorY-0.356)-(0.029000000)*(colorX-0.203)) == 0 and colorX >= 0.028 and colorX <= 0.203 and colorY >= 0.356 and colorY <= 0.385);
  out attribute redChromaticity : Boolean = ((-0.020000000)*(colorY-0.32)-(0.000000000)*(colorX-0.68)) >= 0 and ((0.061000000)*(colorY-0.32)-(-0.061000000)*(colorX-0.66)) >= 0 and ((0.014000000)*(colorY-0.259)-(0.006000000)*(colorX-0.721)) >= 0 and ((-0.055000000)*(colorY-0.265)-(0.055000000)*(colorX-0.735)) >= 0;
  out attribute yellowChromaticity : Boolean = ((((((0.382 > colorY) != (0.425 > colorY)) and colorX < (-0.043000000)*(colorY-0.382)/(0.043000000)+0.618) != (((0.425 > colorY) != (0.406 > colorY)) and colorX < (0.000000000)*(colorY-0.425)/(-0.019000000)+0.575)) != (((0.406 > colorY) != (0.382 > colorY)) and colorX < (0.037000000)*(colorY-0.406)/(-0.024000000)+0.575))) or (((0.006000000)*(colorY-0.382)-(0.000000000)*(colorX-0.612)) == 0 and colorX >= 0.612 and colorX <= 0.618 and colorY >= 0.382 and colorY <= 0.382) or (((-0.043000000)*(colorY-0.382)-(0.043000000)*(colorX-0.618)) == 0 and colorX >= 0.575 and colorX <= 0.618 and colorY >= 0.382 and colorY <= 0.425) or (((0.000000000)*(colorY-0.425)-(-0.019000000)*(colorX-0.575)) == 0 and colorX >= 0.575 and colorX <= 0.575 and colorY >= 0.406 and colorY <= 0.425) or (((0.037000000)*(colorY-0.406)-(-0.024000000)*(colorX-0.575)) == 0 and colorX >= 0.575 and colorX <= 0.612 and colorY >= 0.382 and colorY <= 0.406);
  out attribute chromaticitySupported : Boolean = if requiredColor == Color::white ? whiteChromaticity else if requiredColor == Color::red ? redChromaticity else if requiredColor == Color::green ? greenChromaticity else yellowChromaticity;
  out attribute fixtureSupported : Boolean = factsKnown and lengthM > 0 and nominalArcDeg >= requiredArcMinDeg and nominalArcDeg <= requiredArcMaxDeg and measuredRangeNm >= requiredRangeNm and minimumMeasuredIntensityCd >= minimumIntensityCd and chromaticitySupported and chromaticityEvidenceAccepted and flashSupported and horizontalSectorEvidenceAccepted and verticalSectorEvidenceAccepted and installationPositionEvidenceAccepted and screensEvidenceAccepted;
  out attribute completeComplianceEstablished : Boolean = false;
  in attribute chromaticityEvidenceAccepted : Boolean;
 }
 analysis def Installation {
  doc /* Annex I selected installation constraints. Special layouts/high-speed alternatives require reviewed drawings. Small commensurate shape sizes are externally assessed. Applicable hull/gunwale datum must be used. Does not certify every Annex I clause.*/
  subject encounter;
  in attribute lengthM : Real;
  in attribute breadthM : Real;
  in attribute mastheadHeightM : Real;
  in attribute mastheadAboveSidelightsM : Real;
  in attribute aftAboveForwardM : Real;
  in attribute verticalStackSpacingM : Real;
  in attribute lowestStackHeightM : Real;
  in attribute shapeDiameterM : Real;
  in attribute shapeHeightM : Real;
  in attribute shapeSpacingM : Real;
  in attribute forwardSectorCutoffDeg : Real;
  in attribute aftSectorCutoffDeg : Real;
  in attribute allRoundObscuredDeg : Real;
  in attribute factsKnown : Boolean;
  in attribute powered : Boolean;
  in attribute hasTwoMastheads : Boolean;
  in attribute hasVerticalStack : Boolean;
  in attribute towingStack : Boolean;
  in attribute threeLightsEquallySpaced : Boolean;
  in attribute smallShapeReductionAccepted : Boolean;
  in attribute shapeBlack : Boolean;
  in attribute coneOrDiamond : Boolean;
  in attribute anchorLight : Boolean;
  in attribute highSpeedAlternativeClaimed : Boolean;
  in attribute highSpeedAlternativeEvidenceAccepted : Boolean;
  in attribute horizontalPlacementAccepted : Boolean;
  in attribute trimVisibilityAccepted : Boolean;
  out attribute mastheadMinimumHeightM : Real = if lengthM >= 20 ? (if breadthM > 8 ? 8 else if breadthM > 5 ? breadthM else 5) else if lengthM >= 12 ? 2.5 else 0;
  out attribute mastheadHeightSupported : Boolean = not powered or ((not highSpeedAlternativeClaimed and mastheadHeightM >= mastheadMinimumHeightM) or (highSpeedAlternativeClaimed and highSpeedAlternativeEvidenceAccepted));
  out attribute sidelightSeparationSupported : Boolean = not powered or mastheadAboveSidelightsM >= 1;
  out attribute stackSupported : Boolean = not hasVerticalStack or (verticalStackSpacingM >= 1 and threeLightsEquallySpaced and (towingStack or lowestStackHeightM >= (if lengthM >= 20 ? 4 else 2)));
  out attribute shapeSupported : Boolean = shapeBlack and ((lengthM < 20 and smallShapeReductionAccepted) or (shapeDiameterM >= 0.6 and (not coneOrDiamond or shapeHeightM == shapeDiameterM) and shapeSpacingM >= 1.5));
  out attribute sectorCutoffSupported : Boolean = forwardSectorCutoffDeg >= 1 and forwardSectorCutoffDeg <= 3 and aftSectorCutoffDeg <= 5 and aftSectorCutoffDeg >= 0 and (anchorLight or allRoundObscuredDeg <= 6);
  out attribute installationSupported : Boolean = factsKnown and lengthM > 0 and breadthM > 0 and mastheadHeightSupported and sidelightSeparationSupported and stackSupported and shapeSupported and sectorCutoffSupported and (not hasTwoMastheads or aftAboveForwardM >= 2) and horizontalPlacementAccepted and trimVisibilityAccepted;
  out attribute completeComplianceEstablished : Boolean = false;
 }
 analysis def SoundAppliance {
  doc /* Annex III checks for a fitted whistle/bell. Small efficient alternatives are in Signals. Higher sound level is conservatively used at overlapping 450/800 Hz boundaries. Audibility range is not a detection guarantee; gong level needs separate measurement.*/
  subject encounter;
  in attribute lengthM : Real;
  in attribute fundamentalHz : Real;
  in attribute bandHz : Real;
  in attribute measuredBandDb : Real;
  in attribute forward45Db : Real;
  in attribute otherDirectionsDb : Real;
  in attribute listeningPostDb : Real;
  in attribute bellDb : Real;
  in attribute bellDiameterMm : Real;
  in attribute strikerMassFraction : Real;
  in attribute whistleSpacingM : Real;
  in attribute minimumFrequencyDifferenceHz : Real;
  in attribute conformingWhistleFraction : Real;
  in attribute factsKnown : Boolean;
  in attribute directional : Boolean;
  in attribute forwardAligned : Boolean;
  in attribute positioningReviewed : Boolean;
  in attribute combined : Boolean;
  in attribute twoWhistles : Boolean;
  in attribute higherFrequencyConforms : Boolean;
  in attribute simultaneous : Boolean;
  in attribute manualBell : Boolean;
  in attribute corrosionResistant : Boolean;
  in attribute clearTone : Boolean;
  in attribute bellFitted : Boolean;
  in attribute gongFitted : Boolean;
  in attribute gongDistinct : Boolean;
  out attribute minimumFundamentalHz : Real = if lengthM >= 200 ? 70 else if lengthM >= 75 ? 130 else 250;
  out attribute maximumFundamentalHz : Real = if lengthM >= 200 ? 200 else if lengthM >= 75 ? 350 else 700;
  out attribute minimumBandDb : Real = if lengthM >= 200 ? 143 else if lengthM >= 75 ? 138 else if lengthM >= 20 ? 130 else if bandHz <= 450 ? 120 else if bandHz <= 800 ? 115 else 111;
  out attribute bandValid : Boolean = bandHz >= 180*0.99 and bandHz <= (if lengthM >= 20 ? 700*1.01 else 2100*1.01);
  out attribute combinedSupported : Boolean = if combined ? whistleSpacingM <= 100 and simultaneous and minimumFrequencyDifferenceHz >= 10 and (if twoWhistles ? higherFrequencyConforms else conformingWhistleFraction >= 2.0/3.0) else whistleSpacingM <= 100 or not simultaneous;
  out attribute whistleSupported : Boolean = factsKnown and lengthM > 0 and fundamentalHz >= minimumFundamentalHz and fundamentalHz <= maximumFundamentalHz and bandValid and measuredBandDb >= minimumBandDb and forward45Db >= minimumBandDb-4 and otherDirectionsDb >= minimumBandDb-10 and listeningPostDb <= 110 and (not directional or forwardAligned) and positioningReviewed and combinedSupported;
  out attribute bellSupported : Boolean = not bellFitted or (bellDb >= 110 and (lengthM < 20 or bellDiameterMm >= 300) and strikerMassFraction >= 0.03 and manualBell and corrosionResistant and clearTone);
  out attribute lowerExposurePreferred : Boolean = listeningPostDb <= 100;
  out attribute equipmentSupported : Boolean = whistleSupported and bellSupported and (lengthM < 20 or bellFitted) and (lengthM < 100 or (gongFitted and gongDistinct));
  out attribute completeComplianceEstablished : Boolean = false;
 }
 analysis def ExemptionsAndSpecialCases {
  doc /* Rule 38, Rule 18(e/f), Annex IV/V, Parts 89/90. No new-build grandfathering or self-issued certificate. Geography is externally sourced. No supplemental light grants priority. Annex II/Part 85 and Inland Rule 28 are reserved.*/
  subject encounter;
  in attribute factsKnown : Boolean;
  in attribute constructedBefore19801224 : Boolean;
  in attribute legacyRulesSatisfied : Boolean;
  in attribute metricRepositionOnly : Boolean;
  in attribute certificateClaimed : Boolean;
  in attribute certificateIssued : Boolean;
  in attribute certificateStillApplicable : Boolean;
  in attribute certificateOnboard : Boolean;
  in attribute lawEnforcement : Boolean;
  in attribute publicSafetyAuthorized : Boolean;
  in attribute blueLightChosen : Boolean;
  in attribute redYellowChosen : Boolean;
  in attribute supplementalNonInterfering : Boolean;
  in attribute actualMechanicalRigidConnection : Boolean;
  in attribute movesAsOneVessel : Boolean;
  in attribute mooringBuoyFast : Boolean;
  in attribute specialRiverGeographyReviewed : Boolean;
  in attribute greatLakes : Boolean;
  in attribute westernRivers : Boolean;
  in attribute listed8925Water : Boolean;
  in attribute seaplaneOnWater : Boolean;
  in attribute wigFlight : Boolean;
  in attribute wigOnWater : Boolean;
  in attribute collisionRisk : Boolean;
  in attribute distress : Boolean;
  in attribute assistanceRequired : Boolean;
  in attribute authorizedAnnexIVSignal : Boolean;
  in attribute lengthM : Real;
  out attribute rule38Eligible : Boolean = constructedBefore19801224 and legacyRulesSatisfied;
  out attribute rule38RangeColorExemption : Boolean = rule38Eligible and lengthM < 20;
  out attribute rule38MetricRepositionExemption : Boolean = rule38Eligible and metricRepositionOnly;
  out attribute rule38HorizontalMastheadExemption : Boolean = rule38Eligible and lengthM < 150;
  out attribute rule38PowerLightAlternative : Boolean = rule38Eligible and lengthM >= 12 and lengthM < 20;
  out attribute alternativeCertificateSupported : Boolean = certificateClaimed and certificateIssued and certificateStillApplicable and certificateOnboard;
  out attribute blueLightPermitted : Boolean = lawEnforcement and supplementalNonInterfering;
  out attribute redYellowPermitted : Boolean = publicSafetyAuthorized and supplementalNonInterfering;
  out attribute supplementalPriorityGranted : Boolean = false;
  out attribute compositeUnit : Boolean = actualMechanicalRigidConnection and movesAsOneVessel;
  out attribute anchorRulesApplyToMooring : Boolean = mooringBuoyFast;
  out attribute specialRiverRulesApply : Boolean = specialRiverGeographyReviewed and (greatLakes or westernRivers or listed8925Water);
  out attribute seaplaneGeneralKeepClear : Boolean = seaplaneOnWater;
  out attribute wigFlightKeepClear : Boolean = wigFlight;
  out attribute wigSurfacePowerRules : Boolean = wigOnWater;
  out attribute seaplaneEncounterRulesAlsoApply : Boolean = seaplaneOnWater and collisionRisk;
  out attribute distressUseSupported : Boolean = not authorizedAnnexIVSignal or (distress and assistanceRequired);
  out attribute assessmentSupported : Boolean = factsKnown and lengthM > 0 and (not certificateClaimed or alternativeCertificateSupported) and (not blueLightChosen or blueLightPermitted) and (not redYellowChosen or redYellowPermitted) and distressUseSupported;
  out attribute completeComplianceEstablished : Boolean = false;
 }
 analysis def CandidateAssessment {
  doc /* Combines independently evaluated domains for one consistent candidate and observation. Caller supplies native outputs, not manually invented pass flags. No complete compliance verdict. Nonvisual clear-weather contacts remain unsupported for automatic role selection. Multiple fixture/installations must be checked externally; inputs here are their aggregate evidence results.*/
  subject encounter;
  in attribute factsConsistent : Boolean;
  in attribute inSight : Boolean;
  in attribute inOrNearRestricted : Boolean;
  in attribute generalSupported : Boolean;
  in attribute pairwiseSupported : Boolean;
  in attribute restrictedVisibilitySupported : Boolean;
  in attribute channelSupported : Boolean;
  in attribute tssSupported : Boolean;
  in attribute signalsSupported : Boolean;
  in attribute displaySupported : Boolean;
  in attribute fixturesSupported : Boolean;
  in attribute installationSupported : Boolean;
  in attribute soundSupported : Boolean;
  in attribute specialCasesSupported : Boolean;
  in attribute additionalApplicableClausesReviewed : Boolean;
  out attribute candidateSupported : Boolean = factsConsistent and generalSupported and (if inSight ? pairwiseSupported else inOrNearRestricted and restrictedVisibilitySupported) and channelSupported and tssSupported and signalsSupported and displaySupported and fixturesSupported and installationSupported and soundSupported and specialCasesSupported and specialDisplaysSupported and passageProtocolSupported and distressCatalogSupported and additionalApplicableClausesReviewed;
  out attribute completeComplianceEstablished : Boolean = false;
  in attribute specialDisplaysSupported : Boolean;
  in attribute passageProtocolSupported : Boolean;
  in attribute distressCatalogSupported : Boolean;
 }
 analysis def SnapshotConsistency {
  doc /* Reject inconsistent shared facts across independently evaluated domains. This checks representation consistency, not truth or sufficient sensor evidence. All frames must identify the same vessel, encounter, time and candidate externally.*/
  subject encounter;
  in attribute coreLengthM : Real;
  in attribute channelLengthM : Real;
  in attribute lightLengthM : Real;
  in attribute fixtureLengthM : Real;
  in attribute installationLengthM : Real;
  in attribute soundLengthM : Real;
  in attribute signalLengthM : Real;
  in attribute specialLengthM : Real;
  in attribute coreSight : InlandExtended::Truth;
  in attribute coreRisk : InlandExtended::Truth;
  in attribute generalRisk : InlandExtended::Truth;
  in attribute visibilityRisk : InlandExtended::Truth;
  in attribute coreChannel : InlandExtended::Truth;
  in attribute coreConfined : InlandExtended::Truth;
  in attribute coreCrossing : InlandExtended::Truth;
  in attribute coreNavigatingChannel : InlandExtended::Truth;
  in attribute visibilitySight : Boolean;
  in attribute signalSight : Boolean;
  in attribute channel : Boolean;
  in attribute confined : Boolean;
  in attribute crossing : Boolean;
  in attribute navigatingChannel : Boolean;
  in attribute sailAlsoPowered : Boolean;
  in attribute coreKind : String;
  in attribute lightMode : String;
  in attribute signalMode : String;
  out attribute lengthsAgree : Boolean = coreLengthM > 0 and coreLengthM == channelLengthM and coreLengthM == lightLengthM and coreLengthM == fixtureLengthM and coreLengthM == installationLengthM and coreLengthM == soundLengthM and coreLengthM == signalLengthM and coreLengthM == specialLengthM;
  out attribute sightAgrees : Boolean = coreSight != Truth::unknown and (coreSight == Truth::yes) == visibilitySight and visibilitySight == signalSight;
  out attribute channelAgrees : Boolean = coreChannel != Truth::unknown and (coreChannel == Truth::yes) == channel and coreConfined != Truth::unknown and (coreConfined == Truth::yes) == confined and coreCrossing != Truth::unknown and (coreCrossing == Truth::yes) == crossing and coreNavigatingChannel != Truth::unknown and (coreNavigatingChannel == Truth::yes) == navigatingChannel;
  out attribute modeAgrees : Boolean = (if lightMode == "sail" and sailAlsoPowered ? signalMode == "power" else lightMode == signalMode) and ((coreKind == "sailing" and lightMode == "sail" and not sailAlsoPowered) or (coreKind == "power" and (lightMode == "power" or (lightMode == "sail" and sailAlsoPowered))) or (coreKind == "fishing" and (lightMode == "fishing" or lightMode == "trawling")) or (coreKind == "notUnderCommand" and lightMode == "nuc") or (coreKind == "restrictedManeuverability" and (lightMode == "ram" or lightMode == "dredging" or lightMode == "diving")));
  out attribute consistent : Boolean = lengthsAgree and sightAgrees and channelAgrees and modeAgrees and passageAgrees and coreRisk == generalRisk and coreRisk == visibilityRisk and (not generalRiskPresent or coreRisk != Truth::no) and coreRestricted != Truth::unknown and (coreRestricted == Truth::yes) == lightRestricted and lightRestricted == signalRestricted and signalRestricted == visibilityRestricted;
  out attribute completeComplianceEstablished : Boolean = false;
  in attribute generalRiskPresent : Boolean;
  in attribute lightRestricted : Boolean;
  in attribute signalRestricted : Boolean;
  in attribute visibilityRestricted : Boolean;
  in attribute coreRestricted : InlandExtended::Truth;
  in attribute signalExchangeRequired : Boolean;
  in attribute protocolExchangeRequired : Boolean;
  in attribute signalAgreement : Boolean;
  in attribute protocolAgreement : Boolean;
  in attribute coreAgreement : String;
  out attribute passageAgrees : Boolean = (not signalExchangeRequired or protocolExchangeRequired) and signalAgreement == protocolAgreement and (not (coreAgreement == "portToPort" or coreAgreement == "starboardToStarboard") or protocolAgreement);
 }
 analysis def SpecialDisplays {
  doc /* Conditional alternatives/supplements in Rules20,23-27,30-31. Optional fishing lights must be lower and less visible than principal fishing lights. Dimensions, exact geographic applicability and practicability are externally assessed. Outputs are simultaneous applicable pattern supplements, not automatic hardware commands.*/
  subject encounter;
  in attribute factsKnown : Boolean;
  in attribute greatLakes : Boolean;
  in attribute useGreatLakesPowerAlternative : Boolean;
  in attribute regionalPushAlternativeApplicable : Boolean;
  in attribute chooseRegionalPushAlternative : Boolean;
  in attribute combinedSailingLantern : Boolean;
  in attribute optionalRedOverGreen : Boolean;
  in attribute fishingCloseProximity : Boolean;
  in attribute shootingNets : Boolean;
  in attribute haulingNets : Boolean;
  in attribute netFast : Boolean;
  in attribute pairTrawling : Boolean;
  in attribute purseSeine : Boolean;
  in attribute hamperedByGear : Boolean;
  in attribute pushedAhead : Boolean;
  in attribute towedAlongside : Boolean;
  in attribute alongsideBothSides : Boolean;
  in attribute groupTow : Boolean;
  in attribute towImpracticable : Boolean;
  in attribute assistanceTow : Boolean;
  in attribute unableToTowDisplay : Boolean;
  in attribute allPossibleTowIndication : Boolean;
  in attribute bridgePassageLoweringNecessary : Boolean;
  in attribute anchorCornerAlternative : Boolean;
  in attribute mooredBothSides : Boolean;
  in attribute projectingBarge : Boolean;
  in attribute specialBargeExemptionReviewed : Boolean;
  in attribute specialBargeExemption : Boolean;
  in attribute seaplaneFullDisplayImpossible : Boolean;
  in attribute closestPossibleArrangementReviewed : Boolean;
  in attribute optionalFishingSpacingAccepted : Boolean;
  in attribute mode : InlandExtended::Mode;
  in attribute lengthM : Real;
  out attribute greatLakesAlternativeAvailable : Boolean = greatLakes and mode == Mode::power;
  out attribute greatLakesAlternativePattern : String = "All-round white at second masthead position replaces second masthead and sternlight; same minimum range";
  out attribute regionalPushPattern : String = "Sidelights and two towing lights; no masthead lights under applicable regional provision";
  out attribute sailingOptionalPatternPermitted : Boolean = mode == Mode::sail and not combinedSailingLantern;
  out attribute fishingOptionalPattern : String = if not fishingCloseProximity ? "None" else if purseSeine and hamperedByGear ? "Two yellow lights alternate each second, equal light/dark duration" else if mode == Mode::trawling and shootingNets ? "Two white all-round lights vertically" else if mode == Mode::trawling and haulingNets ? "White over red all-round" else if mode == Mode::trawling and netFast ? "Two red all-round lights vertically" else "None";
  out attribute pairTrawlSearchlightOptional : Boolean = fishingCloseProximity and pairTrawling and mode == Mode::trawling;
  out attribute optionalFishingRangeNm : Real = 1;
  out attribute optionalFishingMinSpacingM : Real = 0.9;
  out attribute groupTowPattern : String = if alongsideBothSides ? "Each outboard stern light; one set of forward/outboard sidelights; one special flashing light" else if towedAlongside ? "Sternlight plus forward sidelights and special flashing light" else if pushedAhead ? "Forward sidelights and special flashing light" else if groupTow ? "Treat group as one vessel except both-side alongside arrangement" else "None";
  out attribute bargeCornerPattern : String = if not anchorCornerAlternative ? "Ordinary Rule30 pattern" else if projectingBarge ? "Mark projecting outboard corners" else if mooredBothSides ? "Mark single/group corner extremities" else "Arrangement applicability review";
  out attribute bargeAlternativeRangeNm : Real = 1;
  out attribute bridgeLoweringPermitted : Boolean = bridgePassageLoweringNecessary;
  out attribute displayAlternativeSupported : Boolean = factsKnown and lengthM > 0 and (not useGreatLakesPowerAlternative or greatLakesAlternativeAvailable) and (not chooseRegionalPushAlternative or (regionalPushAlternativeApplicable and mode == Mode::pushing)) and (not optionalRedOverGreen or sailingOptionalPatternPermitted) and (not (towImpracticable or (assistanceTow and unableToTowDisplay)) or allPossibleTowIndication) and (not seaplaneFullDisplayImpossible or closestPossibleArrangementReviewed) and (not specialBargeExemption or specialBargeExemptionReviewed) and (not fishingCloseProximity or optionalFishingSpacingAccepted);
  out attribute completeComplianceEstablished : Boolean = false;
 }
 analysis def PassageProtocol {
  doc /* Rule34 and special river proposal/holding duties. priorAgreement belongs to this same pair and proposed maneuver; expiry/change must clear it. Planned passage protocol does not veto necessary emergency action. Whistle/radio emission and reception are measured inputs.*/
  subject encounter;
  in attribute factsKnown : Boolean;
  in attribute requiredExchange : Boolean;
  in attribute proposalSent : Boolean;
  in attribute proposalReceived : Boolean;
  in attribute ownAgreement : Boolean;
  in attribute otherAgreement : Boolean;
  in attribute doubt : Boolean;
  in attribute maneuverStarted : Boolean;
  in attribute radioAgreement : Boolean;
  in attribute lawfulAlternative : Boolean;
  in attribute riskResolved : Boolean;
  in attribute downboundWithCurrent : Boolean;
  in attribute specialRiverPriority : Boolean;
  in attribute upboundOpposite : Boolean;
  in attribute holdingForPassage : Boolean;
  in attribute mannerAndPlaceProposed : Boolean;
  in attribute signalInitiated : Boolean;
  in attribute bridgePassageComplete : Boolean;
  in attribute loweredLightsRestored : Boolean;
  in attribute priorAgreement : InlandExtended::Truth;
  out attribute currentAgreement : Boolean = factsKnown and not doubt and (radioAgreement or (ownAgreement and otherAgreement and proposalSent and proposalReceived) or priorAgreement == Truth::yes);
  out attribute dangerSignalRequired : Boolean = doubt;
  out attribute precautionRequired : Boolean = requiredExchange and not currentAgreement;
  out attribute proposalRequired : Boolean = specialRiverPriority and downboundWithCurrent;
  out attribute holdRequired : Boolean = specialRiverPriority and upboundOpposite;
  out attribute protocolSupported : Boolean = factsKnown and (not (maneuverStarted and requiredExchange) or currentAgreement or riskResolved) and (not lawfulAlternative or currentAgreement) and (not proposalRequired or (mannerAndPlaceProposed and signalInitiated)) and (not holdRequired or holdingForPassage) and (not bridgePassageComplete or loweredLightsRestored);
  out attribute agreementRetained : Boolean = currentAgreement and not riskResolved;
  out attribute completeComplianceEstablished : Boolean = false;
 }
 analysis def DistressCatalog {
  doc /* Rule37 / Annex IV catalog. No transmitter or pyrotechnic is actuated. Supplemental canvas/dye cannot replace a required recognized distress signal. Detailed radio coding/channel and emission characteristics require protocol evidence.*/
  subject encounter;
  in attribute signalName : String;
  in attribute factsKnown : Boolean;
  in attribute distress : Boolean;
  in attribute assistanceRequired : Boolean;
  in attribute chosen : Boolean;
  in attribute authorizedRadioEquipment : Boolean;
  in attribute supplementalOnly : Boolean;
  in attribute whiteFlashesPerMinute : Real;
  out attribute listedAnnexIVSignal : Boolean = signalName == "minuteExplosive" or signalName == "continuousFog" or signalName == "redStars" or signalName == "SOS" or signalName == "Mayday" or signalName == "NC" or signalName == "squareFlagBall" or signalName == "flames" or signalName == "redFlare" or signalName == "orangeSmoke" or signalName == "raisedArms" or signalName == "DSC" or signalName == "satelliteDistress" or signalName == "EPIRB" or signalName == "survivalRadio" or (signalName == "highIntensityWhite" and whiteFlashesPerMinute >= 50 and whiteFlashesPerMinute <= 70);
  out attribute radioSignal : Boolean = signalName == "Mayday" or signalName == "DSC" or signalName == "satelliteDistress" or signalName == "EPIRB" or signalName == "survivalRadio";
  out attribute supplementalAid : Boolean = signalName == "orangeCanvas" or signalName == "dyeMarker";
  out attribute useSupported : Boolean = factsKnown and (not chosen or (distress and assistanceRequired and ((listedAnnexIVSignal and (not radioSignal or authorizedRadioEquipment)) or (supplementalOnly and supplementalAid))));
  out attribute completeComplianceEstablished : Boolean = false;
 }
}

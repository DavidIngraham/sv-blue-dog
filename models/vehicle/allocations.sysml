package BlueDogSatisfaction {
    private import BlueDogRequirements::*;
    private import BlueDog::Architecture::missionContext;
    doc /* Design satisfaction allocations, not verification evidence. Physical
     * implementation, quantitative acceptance, and verification remain open.
     * Regulatory classification is a project process obligation, not assigned
     * to a component as though hardware alone could establish authorization.
     */
    satisfy BlueDogRequirements::transportability by missionContext.boat.hullAndRig.handling;
    satisfy BlueDogRequirements::desktopManufacture by missionContext.boat.hullAndRig.printedHull;
    satisfy BlueDogRequirements::serviceability by missionContext.boat.hullAndRig.enclosure;
    satisfy BlueDogRequirements::trafficSafety by missionContext.boat;
    satisfy BlueDogRequirements::operatingBoundary by missionContext.boat.control.boundarySupervisor;
    satisfy BlueDogRequirements::safeRecovery by missionContext.boat;
    satisfy BlueDogRequirements::navigationConspicuity by missionContext.boat.signaling;
    satisfy BlueDogRequirements::environmentalEnvelope by missionContext.boat;
    satisfy BlueDogRequirements::marineDurability by missionContext.boat;
    satisfy BlueDogRequirements::stabilityAndFouling by missionContext.boat;
    satisfy BlueDogRequirements::recoveryPropulsion by missionContext.boat;
    satisfy BlueDogRequirements::recoveryEnergy by missionContext.boat;
    satisfy BlueDogRequirements::telemetryEquipment by missionContext.shoreSupport.monitoringStation;
    satisfy BlueDogRequirements::commandIntegrity by missionContext.boat.communications.commandGateway;
    satisfy BlueDogRequirements::roundTrip by missionContext.boat;
    satisfy BlueDogRequirements::multiDayEndurance by missionContext.boat;
    satisfy BlueDogRequirements::energyAwareness by missionContext.boat.energy.powerManagement;
    satisfy BlueDogRequirements::navigationAndControl by missionContext.boat;
    satisfy BlueDogRequirements::resetRecovery by missionContext.boat;
    satisfy BlueDogRequirements::lowEnergyRecovery by missionContext.boat;
    satisfy BlueDogRequirements::communications by missionContext.boat;
    satisfy BlueDogRequirements::ingressResponse by missionContext.boat;
    satisfy BlueDogRequirements::missionEvidence by missionContext.boat;
    satisfy BlueDogRequirements::gorgeEnvironment by missionContext.boat;
    satisfy BlueDogRequirements::gorgeWind by missionContext.boat;
    satisfy BlueDogRequirements::gorgeWaves by missionContext.boat;
    satisfy BlueDogRequirements::gorgeCurrent by missionContext.boat;
    satisfy BlueDogRequirements::gorgeSurvivalWind by missionContext.boat;
    satisfy BlueDogRequirements::gorgeSurvivalWaves by missionContext.boat;
    satisfy BlueDogRequirements::airTemperature by missionContext.boat;
    satisfy BlueDogRequirements::waterTemperature by missionContext.boat;
    satisfy BlueDogRequirements::humidity by missionContext.boat;
    satisfy BlueDogRequirements::visibility by missionContext.boat;
    satisfy BlueDogRequirements::calmOperation by missionContext.boat;
    satisfy BlueDogRequirements::envelopeTransition by missionContext.boat;
    satisfy BlueDogRequirements::freshwaterExposure by missionContext.boat;
    satisfy BlueDogRequirements::enclosureSealing by missionContext.boat.hullAndRig.enclosure;
    satisfy BlueDogRequirements::wetMechanicalIntegrity by missionContext.boat.hullAndRig;
    satisfy BlueDogRequirements::wetElectricalIntegrity by missionContext.boat.communications;
    satisfy BlueDogRequirements::solarHeating by missionContext.boat.energy.powerManagement;
    satisfy BlueDogRequirements::printedMaterialAging by missionContext.boat.hullAndRig.printedHull;
    satisfy BlueDogRequirements::selfRighting by missionContext.boat;
    satisfy BlueDogRequirements::capsizeControlRecovery by missionContext.boat;
    satisfy BlueDogRequirements::submergedWeedPassage by missionContext.boat;
    satisfy BlueDogRequirements::weedSnagShedding by missionContext.boat;
    satisfy BlueDogRequirements::weedBlockageResponse by missionContext.boat;
    satisfy BlueDogRequirements::recoveryPropulsorWeeds by missionContext.boat;
    satisfy BlueDogRequirements::navigationAvailability by missionContext.boat.navigation;
    satisfy BlueDogRequirements::launchEnergyAdmission by missionContext.boat.energy.powerManagement;
    satisfy BlueDogRequirements::challengeMotorInhibition by missionContext.boat.recovery.recoveryController;

    // Proposed allocations of atomic acceptance leaves; not verification evidence.
    satisfy BlueDogRequirements::energyEstimateCadence by missionContext.boat.energy.powerManagement;
    satisfy BlueDogRequirements::reserveEstimateCadence by missionContext.boat.energy.powerManagement;
    satisfy BlueDogRequirements::energyEstimateAccuracy by missionContext.boat.energy.powerManagement;
    satisfy BlueDogRequirements::conservativeEnergyEstimate by missionContext.boat.energy.powerManagement;
    satisfy BlueDogRequirements::guidanceUpdateCadence by missionContext.boat.control;
    satisfy BlueDogRequirements::sailCommandCadence by missionContext.boat.actuation;
    satisfy BlueDogRequirements::steeringCommandCadence by missionContext.boat.actuation;
    satisfy BlueDogRequirements::positionAccuracy by missionContext.boat.navigation.positionAndAttitude;
    satisfy BlueDogRequirements::headingAccuracy by missionContext.boat.navigation.positionAndAttitude;
    satisfy BlueDogRequirements::restartDeadline by missionContext.boat.recovery.recoveryController;
    satisfy BlueDogRequirements::missionStateRestoration by missionContext.boat.control;
    satisfy BlueDogRequirements::gateProgressRestoration by missionContext.boat.control;
    satisfy BlueDogRequirements::resetRestrictionPreservation by missionContext.boat.control;
    satisfy BlueDogRequirements::lowEnergyEntry by missionContext.boat.energy.powerManagement;
    satisfy BlueDogRequirements::lowEnergyPayloadInhibition by missionContext.boat.energy.powerManagement;
    satisfy BlueDogRequirements::lowEnergyNavigationContinuity by missionContext.boat.control;
    satisfy BlueDogRequirements::lowEnergyCollisionContinuity by missionContext.boat.control.collisionAvoidance;
    satisfy BlueDogRequirements::lowEnergyExit by missionContext.boat.energy.powerManagement;
    satisfy BlueDogRequirements::payloadRestartPermission by missionContext.boat.energy.powerManagement;
    satisfy BlueDogRequirements::telemetryDeliveryCadence by missionContext.boat.communications;
    satisfy BlueDogRequirements::outageAutonomy by missionContext.boat.control;
    satisfy BlueDogRequirements::reconnectCurrentRecord by missionContext.boat.communications;
    satisfy BlueDogRequirements::backlogOrdering by missionContext.boat.communications;
    satisfy BlueDogRequirements::backlogCurrentPriority by missionContext.boat.communications;
    satisfy BlueDogRequirements::ingressDetection by missionContext.boat.recovery.ingressMonitor;
    satisfy BlueDogRequirements::ingressRecoveryRequest by missionContext.boat.recovery.recoveryController;
    satisfy BlueDogRequirements::ingressFlotation by missionContext.boat.hullAndRig;
    satisfy BlueDogRequirements::ingressElectronicsProtection by missionContext.boat.hullAndRig.enclosure;
    satisfy BlueDogRequirements::ingressPositionContinuity by missionContext.boat.communications;
    satisfy BlueDogRequirements::periodicLogCadence by missionContext.boat.recording;
    satisfy BlueDogRequirements::logRetention by missionContext.boat.recording;
    satisfy BlueDogRequirements::criticalEventRecording by missionContext.boat.recording;
    satisfy BlueDogRequirements::logTimestampAccuracy by missionContext.boat.recording;
    satisfy BlueDogRequirements::invalidTimestampMarking by missionContext.boat.recording;
    satisfy BlueDogRequirements::logGapIndication by missionContext.boat.recording;
    satisfy BlueDogRequirements::logInterruptionDurability by missionContext.boat.recording;
    satisfy BlueDogRequirements::reconnectLogPreservation by missionContext.boat.recording;
    satisfy BlueDogRequirements::qualificationPersistence by missionContext.boat.recovery.recoveryController;
    satisfy BlueDogRequirements::unknownQualificationFallback by missionContext.boat.recovery.recoveryController;
    satisfy BlueDogRequirements::navigationValidEpochs by missionContext.boat.navigation;
    satisfy BlueDogRequirements::staleNavigationInvalidation by missionContext.boat.navigation;
    satisfy BlueDogRequirements::navigationDegradedTransition by missionContext.boat.control;
    satisfy BlueDogRequirements::staleNavigationUseInhibition by missionContext.boat.control;
    satisfy BlueDogRequirements::soloTransport by missionContext.boat.hullAndRig.handling;
    satisfy BlueDogRequirements::liftMass by missionContext.boat.hullAndRig.handling;
    satisfy BlueDogRequirements::setupDuration by missionContext.boat.hullAndRig.handling;
    satisfy BlueDogRequirements::packDuration by missionContext.boat.hullAndRig.handling;
    satisfy BlueDogRequirements::soloLaunch by missionContext.boat.hullAndRig.handling;
    satisfy BlueDogRequirements::soloRetrieval by missionContext.boat.hullAndRig.handling;
    satisfy BlueDogRequirements::replacementDuration by missionContext.boat;
    satisfy BlueDogRequirements::nondestructiveService by missionContext.boat;
    satisfy BlueDogRequirements::postServiceSealing by missionContext.boat.hullAndRig.enclosure;
    satisfy BlueDogRequirements::postServiceActuation by missionContext.boat.actuation;
    satisfy BlueDogRequirements::trafficTracking by missionContext.boat.navigation.traffic;
    satisfy BlueDogRequirements::collisionAssessmentCadence by missionContext.boat.control.collisionAvoidance;
    satisfy BlueDogRequirements::avoidanceCommandDeadline by missionContext.boat.control.collisionAvoidance;
    satisfy BlueDogRequirements::trafficAwarenessFault by missionContext.boat.control.collisionAvoidance;
    satisfy BlueDogRequirements::boundaryEvaluationCadence by missionContext.boat.control.boundarySupervisor;
    satisfy BlueDogRequirements::boundaryAvoidanceDeadline by missionContext.boat.control.boundarySupervisor;
    satisfy BlueDogRequirements::boundaryAvoidanceRecording by missionContext.boat.recording;
    satisfy BlueDogRequirements::boundaryStartInhibition by missionContext.boat.control.boundarySupervisor;
    satisfy BlueDogRequirements::boundaryDegradedEvidence by missionContext.boat.control.boundarySupervisor;
    satisfy BlueDogRequirements::abortLatchDeadline by missionContext.boat.recovery.recoveryController;
    satisfy BlueDogRequirements::recoveryTelemetryCadence by missionContext.boat.communications;
    satisfy BlueDogRequirements::motorIsolationDeadline by missionContext.boat.recovery.motorSystem;
    satisfy BlueDogRequirements::isolationRestartInhibition by missionContext.boat.recovery.motorSystem;
    satisfy BlueDogRequirements::manualControlLossShutdown by missionContext.boat.recovery.recoveryController;
    satisfy BlueDogRequirements::controlLossLocationContinuity by missionContext.boat.communications;
    satisfy BlueDogRequirements::navigationLightPresentation by missionContext.boat.signaling;
    satisfy BlueDogRequirements::navigationShapePresentation by missionContext.boat.signaling;
    satisfy BlueDogRequirements::navigationSoundPresentation by missionContext.boat.signaling;
    satisfy BlueDogRequirements::signalingModeDeadline by missionContext.boat.signaling;
    satisfy BlueDogRequirements::signalingFaultRecording by missionContext.boat.recording;
    satisfy BlueDogRequirements::signalingFaultReporting by missionContext.boat.communications;
    satisfy BlueDogRequirements::telemetryDisplayContent by missionContext.shoreSupport.monitoringStation;
    satisfy BlueDogRequirements::telemetryStaleIndication by missionContext.shoreSupport.monitoringStation;
    satisfy BlueDogRequirements::telemetryIdentityPreservation by missionContext.shoreSupport.monitoringStation;
    satisfy BlueDogRequirements::telemetryDuplicateSuppression by missionContext.shoreSupport.monitoringStation;
    satisfy BlueDogRequirements::unauthenticatedCommandRejection by missionContext.boat.communications.commandGateway;
    satisfy BlueDogRequirements::replayCommandRejection by missionContext.boat.communications.commandGateway;
    satisfy BlueDogRequirements::expiredCommandRejection by missionContext.boat.communications.commandGateway;
    satisfy BlueDogRequirements::acceptedCommandDeadline by missionContext.boat.communications.commandGateway;
    satisfy BlueDogRequirements::onboardAcknowledgmentDeadline by missionContext.boat.communications.commandGateway;
    satisfy BlueDogRequirements::acknowledgmentQueueing by missionContext.boat.communications.commandGateway;
    satisfy BlueDogRequirements::externalControlDisqualification by missionContext.boat.recovery.recoveryController;
    satisfy BlueDogRequirements::visibilityNavigationCapability by missionContext.boat.navigation;
    satisfy BlueDogRequirements::visibilityTrafficCapability by missionContext.boat.navigation.traffic;
    satisfy BlueDogRequirements::restrictedVisibilityEntry by missionContext.boat.control;
    satisfy BlueDogRequirements::restrictedVisibilityEvidence by missionContext.boat.recording;
    satisfy BlueDogRequirements::restrictedVisibilityCollisionAssessment by missionContext.boat.control.collisionAvoidance;
    satisfy BlueDogRequirements::survivalEntryDeadline by missionContext.boat.control;
    satisfy BlueDogRequirements::survivalTransitionRecording by missionContext.boat.recording;
    satisfy BlueDogRequirements::sailingResumptionDeadline by missionContext.boat.control;
    satisfy BlueDogRequirements::sailingResumptionInhibition by missionContext.boat.control;
    satisfy BlueDogRequirements::resumptionBlockEvidence by missionContext.boat.recording;
    satisfy BlueDogRequirements::wetMechanismTravel by missionContext.boat.hullAndRig;
    satisfy BlueDogRequirements::wetJointIntegrity by missionContext.boat.hullAndRig;
    satisfy BlueDogRequirements::wetConductorResistance by missionContext.boat.energy;
    satisfy BlueDogRequirements::wetInsulationResistance by missionContext.boat.energy;
    satisfy BlueDogRequirements::hotSunElectronicsOperation by missionContext.boat;
    satisfy BlueDogRequirements::hotSunBatteryTemperature by missionContext.boat.energy.storage;
    satisfy BlueDogRequirements::batteryChargeTemperatureInhibition by missionContext.boat.energy.powerManagement;
    satisfy BlueDogRequirements::rightingDeadline by missionContext.boat.hullAndRig;
    satisfy BlueDogRequirements::capsizeRigRetention by missionContext.boat.hullAndRig;
    satisfy BlueDogRequirements::capsizeBallastRetention by missionContext.boat.hullAndRig.keelAndBallast;
    satisfy BlueDogRequirements::capsizeElectronicsSealing by missionContext.boat.hullAndRig.enclosure;
    satisfy BlueDogRequirements::controlRecoveryDeadline by missionContext.boat.control;
    satisfy BlueDogRequirements::capsizeGateProgressRetention by missionContext.boat.control.missionManager;
    satisfy BlueDogRequirements::capsizeQualificationRetention by missionContext.boat.recovery.recoveryController;
    satisfy BlueDogRequirements::capsizeRestrictionRetention by missionContext.boat.control;
    satisfy BlueDogRequirements::weedPassageSpeed by missionContext.boat;
    satisfy BlueDogRequirements::weedPassageSteering by missionContext.boat.actuation;
    satisfy BlueDogRequirements::weedSnagSpeedRecovery by missionContext.boat;
    satisfy BlueDogRequirements::weedSnagSteeringRecovery by missionContext.boat.actuation;
    satisfy BlueDogRequirements::weedBlockageFault by missionContext.boat.recording;
    satisfy BlueDogRequirements::weedBlockageContingency by missionContext.boat.control;
    satisfy BlueDogRequirements::weedBlockageLocation by missionContext.boat.communications;
    satisfy BlueDogRequirements::poweredWeedSpeed by missionContext.boat.recovery.motorSystem;
    satisfy BlueDogRequirements::poweredWeedCurrent by missionContext.boat.recovery.motorSystem;
    satisfy BlueDogRequirements::poweredWeedTemperature by missionContext.boat.recovery.motorSystem;
    satisfy BlueDogRequirements::lockedPropulsorShutdown by missionContext.boat.recovery.motorSystem;
    satisfy BlueDogRequirements::motorQualificationInvariant by missionContext.boat.recovery.recoveryController;
    satisfy BlueDogRequirements::freshRecoveryCommand by missionContext.boat.recovery.recoveryController;
    satisfy BlueDogRequirements::ingressEventDeadline by missionContext.boat.recording;
    satisfy BlueDogRequirements::qualificationRestoration by missionContext.boat.recovery.recoveryController;
    satisfy BlueDogRequirements::sustainedReserveProtection by missionContext.boat.energy;
    satisfy BlueDogRequirements::peakSupplyCapability by missionContext.boat.energy;
    satisfy BlueDogRequirements::cruisePerformance by missionContext.boat;
    satisfy BlueDogRequirements::legProgress by missionContext.boat;
    satisfy BlueDogRequirements::passageDuration by missionContext.boat;
    satisfy BlueDogRequirements::missionReliability by missionContext.boat;
    satisfy BlueDogRequirements::missionSuccessProbability by missionContext.boat;
    satisfy BlueDogRequirements::failureRateBudget by missionContext.boat;
    satisfy BlueDogRequirements::windObservation by missionContext.boat.navigation.wind;
    satisfy BlueDogRequirements::windSampleCadence by missionContext.boat.navigation.wind;
    satisfy BlueDogRequirements::windSpeedAccuracy by missionContext.boat.navigation.wind;
    satisfy BlueDogRequirements::windDirectionAccuracy by missionContext.boat.navigation.wind;
    satisfy BlueDogRequirements::windStaleInvalidation by missionContext.boat.navigation.wind;
    satisfy BlueDogRequirements::invalidWindUseInhibition by missionContext.boat.control;
    satisfy BlueDogRequirements::windLossResponse by missionContext.boat.control;
    satisfy BlueDogRequirements::windSensingEndurance by missionContext.boat.navigation.wind;

    // Logical responsibility allocations for the SRR challenge baseline.
    // These assert intended design responsibility, not demonstrated compliance.
    satisfy GorgeChallenge::overallLength by missionContext.boat;
    satisfy GorgeChallenge::trafficNonInterference by missionContext.boat.control.collisionAvoidance;
    satisfy GorgeChallenge::safetyCapabilityAbort by missionContext.boat.recovery.recoveryController;
    satisfy GorgeChallenge::autonomousShoreRecovery by missionContext.boat.recovery.recoveryController;
    satisfy GorgeChallenge::abortAlert by missionContext.boat.communications;
    satisfy GorgeChallenge::noLittering by missionContext.boat;
    satisfy GorgeChallenge::casualtyFlotation by missionContext.boat.hullAndRig;
    satisfy GorgeChallenge::majorComponentRetention by missionContext.boat.hullAndRig;
    satisfy GorgeChallenge::capsizeRecovery by missionContext.boat;
    satisfy GorgeChallenge::unattachedPassage by missionContext.boat.control.missionManager;
    satisfy GorgeChallenge::communicationOutageAutonomy by missionContext.boat.control.missionManager;
    satisfy GorgeChallenge::forecastAdmission by missionContext.boat.control.missionManager;
    satisfy GorgeChallenge::weatherOutageContinuation by missionContext.boat.control.missionManager;
    satisfy GorgeChallenge::courseRecoveryReserve by missionContext.boat.energy.powerManagement;
    satisfy GorgeChallenge::reserveAbort by missionContext.boat.recovery.recoveryController;
    satisfy GorgeChallenge::nightOperation by missionContext.boat;
    satisfy GorgeChallenge::abortPersistence by missionContext.boat.recovery.recoveryController;
    satisfy GorgeChallenge::recoveryConspicuity by missionContext.boat.signaling;
}

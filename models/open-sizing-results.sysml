package BlueDogOpenSizingResults {
    part nominal_5ms_0Input : BlueDogOpenSizing::Candidate {
        attribute :>> design = (1.2541225695803222, 0.51618882102018093, 0.6828816951743657, 5.0262595387736742, 0.04258250046413916, 0.36805077718286661, 0.019672063235208322, 0.2009525970352421, 2.4229905167626232e-15, -0.08027663276052377, 201.46499292743098, 0.22105735209305738, 0.17717500011526888, 0.14714757167995152, 0.5, 0.60000000000000009, 0.40000000000000002, 2.8000000000000003, 1, 0.029750747756729805);
        attribute :>> scenario = (5, 1, 1, 1.3198306643973305, 35.276582883175266, 11.999999999999877, 4.9409099386793027, -0.75848132318470007, 19.377640180018346);
    }
    analysis nominal_5ms_0 : BlueDogOpenSizing::Audit { subject :>> trial = nominal_5ms_0Input; }
    part nominal_5ms_1Input : BlueDogOpenSizing::Candidate {
        attribute :>> design = (1.2541225695803222, 0.51618882102018093, 0.6828816951743657, 5.0262595387736742, 0.04258250046413916, 0.36805077718286661, 0.019672063235208322, 0.2009525970352421, 2.4229905167626232e-15, -0.08027663276052377, 201.46499292743098, 0.22105735209305738, 0.17717500011526888, 0.14714757167995152, 0.5, 0.60000000000000009, 0.40000000000000002, 2.8000000000000003, 1, 0.029750747756729805);
        attribute :>> scenario = (5, 0, 1, 1.1751033591767406, 152.90072242899902, 11.993044177902867, -2.1028137084828638, 0.33081658744367815, -7.4368171601952238);
    }
    analysis nominal_5ms_1 : BlueDogOpenSizing::Audit { subject :>> trial = nominal_5ms_1Input; }
    part stress_cases_0Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (3, 1, 1, 0.89589760009474873, 35.846779194671569, 11.999999999999115, 5.444508103965191, -0.4483682541450591, 13.402108344137581);
    }
    analysis stress_cases_0 : BlueDogOpenSizing::Audit { subject :>> trial = stress_cases_0Input; }
    part stress_cases_1Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (3, 0, 1, 0.80697527502024458, 148.41793478185608, 12, -1.8895719480708948, 0.16164459590183355, -4.021872996138903);
    }
    analysis stress_cases_1 : BlueDogOpenSizing::Audit { subject :>> trial = stress_cases_1Input; }
    part stress_cases_2Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (5, 1, 1, 1.3191764583992984, 55.88755574624544, 7.6294815062476982, 3.2203320697712261, -0.23374272344509706, 16.661537867239502);
    }
    analysis stress_cases_2 : BlueDogOpenSizing::Audit { subject :>> trial = stress_cases_2Input; }
    part stress_cases_3Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (5, 0, 1, 1.3141096220130659, 122.07996285982836, 8.139009843159613, -0.53514390514478194, 0.041329518635841112, -3.0539785015923471);
    }
    analysis stress_cases_3 : BlueDogOpenSizing::Audit { subject :>> trial = stress_cases_3Input; }
    part stress_cases_4Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (15, 1, 1, 1.1066763767832919, 46.938264285744282, 0.97990053393839283, 5.598026832676906, -0.42452749586782446, 19.471220634490088);
    }
    analysis stress_cases_4 : BlueDogOpenSizing::Audit { subject :>> trial = stress_cases_4Input; }
    part stress_cases_5Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (15, 0, 1, 1.5301467182557618, 129.99900520298036, 1.2086299091113792, -0.90973291155954605, 0.064258001094724904, -6.9727800645502374);
    }
    analysis stress_cases_5 : BlueDogOpenSizing::Audit { subject :>> trial = stress_cases_5Input; }
    part stress_cases_6Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (5, 1, 1.5, 1.1053511679679384, 47.525618945351525, 7.7640452582326818, 4.8910673888342906, -0.28509602702781223, 17.775015612846261);
    }
    analysis stress_cases_6 : BlueDogOpenSizing::Audit { subject :>> trial = stress_cases_6Input; }
    part stress_cases_7Input : BlueDogOpenSizing::Candidate {
        attribute :>> design = (0.95828998433727941, 0.5581011213697199, 0.78101572333569091, 4.8189905119875016, 0.030598049391311256, 0.28480984930422693, 0.026639593530651928, 0.24889651941227492, 1.4333079086495719e-15, -0.15568999615595264, 201.08667866036706, 0.22042930095686777, 0.13492640136752077, 0.1547749865683804, 0.5, 0.60000000000000009, 0.40000000000000002, 2.6000000000000001, 1.2000000000000002, 0.029750747756729732);
        attribute :>> scenario = (5, 0, 1.5, 1.2328652428798876, 126.21382750252403, 9.8008835020374168, -1.0041432673289776, 0.062412466298930269, -5.0960119048632517);
    }
    analysis stress_cases_7 : BlueDogOpenSizing::Audit { subject :>> trial = stress_cases_7Input; }
    part route : BlueDogSizingRoute::Profile {
        attribute :>> waterVMG = (stress_cases_0.rows#(49), stress_cases_1.rows#(49), stress_cases_2.rows#(49), stress_cases_3.rows#(49), stress_cases_4.rows#(49), stress_cases_5.rows#(49), stress_cases_6.rows#(49), stress_cases_7.rows#(49));
    }
    analysis routeAudit : BlueDogSizingRoute::Assessment { subject :>> profile = route; }
}

package BlueDogHullLengthResults {
    doc /* Generated by scripts/study_hull_length.py --publish from saved search inputs.
     * Numerical outputs are recomputed by SearchAudit; no physical evidence is accepted. */
    part full_envelope : BlueDogDesignSearch::SearchResult {
        attribute :>> label = "full_envelope";
        attribute :>> design = (2.0213606892947711, 0.20000000000000018, 1.8, 2.2222222222222232, 0.022527337984553759, 0.84999999999999998, 0.016651513399044509, 0.22202017865393006, 9.9552150727630657, -0.074067287350242067, 204.24019673055403, 0.225664553177957, 0.46814212543247813);
        attribute :>> evidenceAccepted = false;
        part point1 :> points {
            attribute :>> index = 1;
            attribute :>> operatingValues = (1.2152392202367563, 32.959676181225369, 11.647662789432715, 5.0234728390582362, -0.81601393229002639, 13.381478472420135);
        }
        part point2 :> points {
            attribute :>> index = 2;
            attribute :>> operatingValues = (1.1319579800100872, 147.01538472428123, 12, -0.88076879168508171, 0.14243356426572618, -2.1902688562142458);
        }
        part point3 :> points {
            attribute :>> index = 3;
            attribute :>> operatingValues = (1.9459464737862442, 56.814999601084935, 7.398966753003025, 2.5782735190597101, -0.40499323582715618, 16.93608154421856);
        }
        part point4 :> points {
            attribute :>> index = 4;
            attribute :>> operatingValues = (2.0560538402961708, 119.00174535022933, 9.3955750651553256, 0.096180051458016891, -0.015207437982965644, 0.79301231409580453);
        }
        part point5 :> points {
            attribute :>> index = 5;
            attribute :>> operatingValues = (1.595669485130554, 49.314734621698079, 1.0350045710670621, 4.5960349332934562, -0.73279424157952278, 19.471220634490706);
        }
        part point6 :> points {
            attribute :>> index = 6;
            attribute :>> operatingValues = (2.2608961859285732, 121.99543492981762, 1.0736747565037179, 0.043351124271488573, -0.0067925431387791946, 0.43283205582938677);
        }
        part point7 :> points {
            attribute :>> index = 7;
            attribute :>> operatingValues = (1.5690624146497982, 46.419369513321897, 7.5313231316831155, 4.1285868163453543, -0.61933348847948011, 17.601440593761943);
        }
        part point8 :> points {
            attribute :>> index = 8;
            attribute :>> operatingValues = (1.7967947233474466, 128.00451725693515, 10.643494019450641, -0.363162433170368, 0.054817732236504213, -2.3014877861132703);
        }
    }
    analysis full_envelopeAudit : BlueDogDesignSearch::SearchAudit { subject :>> trial = full_envelope; in attribute :>> designUpper = BlueDogHullLengthStudy::limits.relaxedUpper; }
    part nominal_5ms : BlueDogDesignSearch::SearchResult {
        attribute :>> label = "nominal_5ms";
        attribute :>> design = (2.8934202985711508, 0.20000000000000001, 1.3999838538658678, 2.8571758087981309, 0.014887803546460406, 0.8499999999999952, 0.010701302750908488, 0.14268403667854329, 13, -0.035380428024675378, 204.82382896348247, 0.22663345897647169, 0.53151824036083894);
        attribute :>> evidenceAccepted = false;
        part point3 :> points {
            attribute :>> index = 3;
            attribute :>> operatingValues = (1.8904425190681762, 33.156540490309062, 11.355976603759675, 7.7922482190869395, -3.9576784187174283, 19.471220642665024);
        }
        part point4 :> points {
            attribute :>> index = 4;
            attribute :>> operatingValues = (1.7128114238809247, 148.28284206680217, 12, -1.809870295082094, 0.92030594240707941, -4.3247404344225728);
        }
    }
    analysis nominal_5msAudit : BlueDogDesignSearch::SearchAudit { subject :>> trial = nominal_5ms; in attribute :>> designUpper = BlueDogHullLengthStudy::limits.relaxedUpper; }
    part fixed_2 : BlueDogDesignSearch::SearchResult {
        attribute :>> label = "fixed_2";
        attribute :>> design = (2, 0.47614221428931897, 1.8, 2.2222222222221877, 0.019642075249149307, 0.84999999999999998, 0.014540840233043185, 0.19387786977396973, 2.0000000000000067, -0.015342377471143809, 207.31066962354961, 0.23076193954936808, 0.79504014403919476);
        attribute :>> evidenceAccepted = false;
        part point3 :> points {
            attribute :>> index = 3;
            attribute :>> operatingValues = (1.8662001384064648, 33.771793877833815, 12, 7.7619559961472397, -6.5205938349685972, 19.471220634887189);
        }
        part point4 :> points {
            attribute :>> index = 4;
            attribute :>> operatingValues = (1.7426013509558702, 144.78137223786479, 11.917371184074725, -1.4087256448353553, 1.1840171838714397, -3.5991282259529136);
        }
    }
    analysis fixed_2Audit : BlueDogDesignSearch::SearchAudit { subject :>> trial = fixed_2; in attribute :>> designUpper = BlueDogHullLengthStudy::limits.relaxedUpper; }
    part fixed_3_5 : BlueDogDesignSearch::SearchResult {
        attribute :>> label = "fixed_3_5";
        attribute :>> design = (3.5, 0.20000000000000001, 1.4577576941528432, 2.743940241950205, 0.014877516026517002, 0.84999999999999998, 0.010499999999999621, 0.14000000000000001, 13, -0.037594139789600425, 205.15839494430048, 0.22718888223871583, 0.56620142092532033);
        attribute :>> evidenceAccepted = false;
        part point3 :> points {
            attribute :>> index = 3;
            attribute :>> operatingValues = (1.9004831905787678, 33.869184568948427, 11.431156913232238, 7.8540756181012519, -3.5903516058010467, 19.47122063885174);
        }
        part point4 :> points {
            attribute :>> index = 4;
            attribute :>> operatingValues = (1.713995801010487, 147.65115648392765, 11.999999999999986, -1.800732096211771, 0.82357300522864563, -4.2324635614975925);
        }
    }
    analysis fixed_3_5Audit : BlueDogDesignSearch::SearchAudit { subject :>> trial = fixed_3_5; in attribute :>> designUpper = BlueDogHullLengthStudy::limits.relaxedUpper; }
    part fixed_5 : BlueDogDesignSearch::SearchResult {
        attribute :>> label = "fixed_5";
        attribute :>> design = (5, 0.20000000000000115, 1.5753770846780761, 2.5390746373698763, 0.015486144923271718, 0.84999999999999931, 0.010500000000000859, 0.14000000000001098, 12.999999999999973, -0.038969276456328375, 205.92215089801155, 0.22845681695922729, 0.64585550403844438);
        attribute :>> evidenceAccepted = false;
        part point3 :> points {
            attribute :>> index = 3;
            attribute :>> operatingValues = (1.8708144089555885, 35.032709814200636, 11.861734551362549, 8.211504827693755, -3.3711068549908667, 19.471220634489747);
        }
        part point4 :> points {
            attribute :>> index = 4;
            attribute :>> operatingValues = (1.646633176057168, 147.87239245159319, 12, -2.0180007955622701, 0.82776553533740937, -4.3227267661782438);
        }
    }
    analysis fixed_5Audit : BlueDogDesignSearch::SearchAudit { subject :>> trial = fixed_5; in attribute :>> designUpper = BlueDogHullLengthStudy::limits.relaxedUpper; }
    part fixed_8 : BlueDogDesignSearch::SearchResult {
        attribute :>> label = "fixed_8";
        attribute :>> design = (8, 0.20000000000000001, 1.8, 2.2222222222222201, 0.02082051608058056, 0.84999999999999998, 0.010499999999999732, 0.14000000000000001, 13, -0.015377828969870139, 206.88745200142691, 0.23005934297408953, 0.75077492236513632);
        attribute :>> evidenceAccepted = false;
        part point3 :> points {
            attribute :>> index = 3;
            attribute :>> operatingValues = (1.6812088157761649, 35.306442014514033, 11.999999999999984, 8.3191141307840013, -5.9315289698729661, 18.357119393866405);
        }
        part point4 :> points {
            attribute :>> index = 4;
            attribute :>> operatingValues = (1.467700774308643, 150.56959400384343, 11.969206846367332, -2.5295156023252554, 1.8044035088821602, -4.8661563942156114);
        }
    }
    analysis fixed_8Audit : BlueDogDesignSearch::SearchAudit { subject :>> trial = fixed_8; in attribute :>> designUpper = BlueDogHullLengthStudy::limits.relaxedUpper; }
    part fixed_12 : BlueDogDesignSearch::SearchResult {
        attribute :>> label = "fixed_12";
        attribute :>> design = (12, 0.20000000000000001, 1.799999999999998, 2.2222222222222254, 0.025943823745918297, 0.84999999999999998, 0.010499999999999734, 0.14000000000000001, 12.324320653168364, -0.013106924047169871, 206.4852907158552, 0.2293917026698859, 0.70903438195905122);
        attribute :>> evidenceAccepted = false;
        part point3 :> points {
            attribute :>> index = 3;
            attribute :>> operatingValues = (1.4583450527383628, 35.285418347758757, 11.999999999996934, 8.3588009259741405, -5.8593775114789022, 15.785311458205584);
        }
        part point4 :> points {
            attribute :>> index = 4;
            attribute :>> operatingValues = (1.2440722813850791, 154.83183084731218, 11.915506878028653, -3.4876947613913156, 2.4450749698212135, -5.277453055977217);
        }
    }
    analysis fixed_12Audit : BlueDogDesignSearch::SearchAudit { subject :>> trial = fixed_12; in attribute :>> designUpper = BlueDogHullLengthStudy::limits.relaxedUpper; }
    part fixed_20 : BlueDogDesignSearch::SearchResult {
        attribute :>> label = "fixed_20";
        attribute :>> design = (20, 0.20000000000000001, 0.31976799678644818, 4.4999999999999973, 0.043045360877779611, 0.81075764814311002, 0.010500000000000001, 0.14000000000000001, 2, -0.0072512739360877931, 200.36831198828025, 0.21923671837704103, 0.30000000000000338);
        attribute :>> evidenceAccepted = false;
        part point3 :> points {
            attribute :>> index = 3;
            attribute :>> operatingValues = (0.56504879841619338, 35.003492931614588, 11.999999999999998, 6.3702065438258941, -4.7711691120434114, 2.7248959879533032);
        }
        part point4 :> points {
            attribute :>> index = 4;
            attribute :>> operatingValues = (0.56504879848385481, 147.57502319933144, 12, -3.605010116706298, 2.7002516103511098, -1.5494873291361415);
        }
    }
    analysis fixed_20Audit : BlueDogDesignSearch::SearchAudit { subject :>> trial = fixed_20; in attribute :>> designUpper = BlueDogHullLengthStudy::limits.relaxedUpper; }
}

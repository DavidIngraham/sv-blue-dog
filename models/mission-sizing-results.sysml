package BlueDogMissionSizingResults {
analysis printed_infill0 { out attribute rows : ScalarValues::Real [*] ordered nonunique = BlueDogMissionSizing::EvaluateCase((2, 0.56132937295449747, 0.94381751326867858, 5.1019038679847064, 0.19833749935547398, 0.91539362654635992, 0.011940051264105368, 0.14752156023597496, 9.9264004611922161, -0.013066776771430755, 205.60153621718206, 0.22792455467863401, 0.61514086255999501, 0.15536248031116986, 0.5, 0.60000000000000009, 0.60000000000000009, 5, 1, 0.029750747756729794), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 0, 15, 0.59999999999999998, 0.00080000000000000004, 0.040000000000000001, 0.02), (5, 1, 1, 1.2431083539470724, 37.482385314642954, 12, 1.6067878302328715, 0.12205335941424167, 8.4167143456374234)); }
analysis printed_infill1 { out attribute rows : ScalarValues::Real [*] ordered nonunique = BlueDogMissionSizing::EvaluateCase((2, 0.56132937295449747, 0.94381751326867858, 5.1019038679847064, 0.19833749935547398, 0.91539362654635992, 0.011940051264105368, 0.14752156023597496, 9.9264004611922161, -0.013066776771430755, 205.60153621718206, 0.22792455467863401, 0.61514086255999501, 0.15536248031116986, 0.5, 0.60000000000000009, 0.60000000000000009, 5, 1, 0.029750747756729794), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 0, 15, 0.59999999999999998, 0.00080000000000000004, 0.040000000000000001, 0.02), (5, 0, 1, 1.0989199847344235, 135.52957898944388, 8.8500961975006778, -0.41644471220870294, -0.031595393169212116, -1.7521306406351904)); }
analysis printed_infill2 { out attribute rows : ScalarValues::Real [*] ordered nonunique = BlueDogMissionSizing::EvaluateCase((2, 0.56132937295449747, 0.94381751326867858, 5.1019038679847064, 0.19833749935547398, 0.91539362654635992, 0.011940051264105368, 0.14752156023597496, 9.9264004611922161, -0.013066776771430755, 205.60153621718206, 0.22792455467863401, 0.61514086255999501, 0.15536248031116986, 0.5, 0.60000000000000009, 0.60000000000000009, 5, 1, 0.029750747756729794), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 0, 15, 0.59999999999999998, 0.00080000000000000004, 0.040000000000000001, 0.02), (8, 1, 1, 1.8328115038368431, 36.552989333709199, 11.999999999999996, 1.9407625108195994, 0.15144746902682726, 19.471220634490706)); }
analysis printed_infill3 { out attribute rows : ScalarValues::Real [*] ordered nonunique = BlueDogMissionSizing::EvaluateCase((2, 0.56132937295449747, 0.94381751326867858, 5.1019038679847064, 0.19833749935547398, 0.91539362654635992, 0.011940051264105368, 0.14752156023597496, 9.9264004611922161, -0.013066776771430755, 205.60153621718206, 0.22792455467863401, 0.61514086255999501, 0.15536248031116986, 0.5, 0.60000000000000009, 0.60000000000000009, 5, 1, 0.029750747756729794), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 0, 15, 0.59999999999999998, 0.00080000000000000004, 0.040000000000000001, 0.02), (8, 0, 1, 1.4666233831586744, 138.7809826261371, 6.5379237893094171, -0.53229739484305938, -0.040610715497749084, -3.9697304354105185)); }
analysis printed_infillRoute { out attribute rows : ScalarValues::Real [*] ordered nonunique = BlueDogMissionSizing::Route((0.96485790212881217, 0.77858660103621358, 1.434497646170686, 1.0941627811279451), (0.94999999999999996, 0.5, 0.5, 0.5, 1, 100000, 72)); }
analysis printed_ribs0 { out attribute rows : ScalarValues::Real [*] ordered nonunique = BlueDogMissionSizing::EvaluateCase((2, 0.60443680370320818, 1.1782673034533631, 5.2091181580933146, 0.14177613862996261, 0.71481970699992281, 0.012084584191152607, 0.128168407768877, 11.673594325500416, -0.017302668016087763, 207.46827297665885, 0.23102358171724305, 0.80857334954099014, 0.16320739114528268, 0.49999999999999994, 0.60000000000000009, 0.40000000000000002, 4.8000000000000007, 0.40000000000000002, 0.02975074775672985), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 1, 15, 0.59999999999999998, 0.00080000000000000004, 0.040000000000000001, 0.02), (5, 1, 1, 1.4213234818090041, 36.888011274705597, 11.999999999999991, 2.4249426487029861, 0.36948167187890135, 9.2741900203734993)); }
analysis printed_ribs1 { out attribute rows : ScalarValues::Real [*] ordered nonunique = BlueDogMissionSizing::EvaluateCase((2, 0.60443680370320818, 1.1782673034533631, 5.2091181580933146, 0.14177613862996261, 0.71481970699992281, 0.012084584191152607, 0.128168407768877, 11.673594325500416, -0.017302668016087763, 207.46827297665885, 0.23102358171724305, 0.80857334954099014, 0.16320739114528268, 0.49999999999999994, 0.60000000000000009, 0.40000000000000002, 4.8000000000000007, 0.40000000000000002, 0.02975074775672985), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 1, 15, 0.59999999999999998, 0.00080000000000000004, 0.040000000000000001, 0.02), (5, 0, 1, 1.1108225186773386, 152.42440894763723, 10.138251175730389, -1.1855700102233531, -0.18030643455377415, -2.8572650745897086)); }
analysis printed_ribs2 { out attribute rows : ScalarValues::Real [*] ordered nonunique = BlueDogMissionSizing::EvaluateCase((2, 0.60443680370320818, 1.1782673034533631, 5.2091181580933146, 0.14177613862996261, 0.71481970699992281, 0.012084584191152607, 0.128168407768877, 11.673594325500416, -0.017302668016087763, 207.46827297665885, 0.23102358171724305, 0.80857334954099014, 0.16320739114528268, 0.49999999999999994, 0.60000000000000009, 0.40000000000000002, 4.8000000000000007, 0.40000000000000002, 0.02975074775672985), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 1, 15, 0.59999999999999998, 0.00080000000000000004, 0.040000000000000001, 0.02), (8, 1, 1, 2.0243674982392714, 36.656400691030839, 11.145547911884041, 2.8271984521720981, 0.4411743804658812, 19.4712206344904)); }
analysis printed_ribs3 { out attribute rows : ScalarValues::Real [*] ordered nonunique = BlueDogMissionSizing::EvaluateCase((2, 0.60443680370320818, 1.1782673034533631, 5.2091181580933146, 0.14177613862996261, 0.71481970699992281, 0.012084584191152607, 0.128168407768877, 11.673594325500416, -0.017302668016087763, 207.46827297665885, 0.23102358171724305, 0.80857334954099014, 0.16320739114528268, 0.49999999999999994, 0.60000000000000009, 0.40000000000000002, 4.8000000000000007, 0.40000000000000002, 0.02975074775672985), (9.8066499999999994, 1.2250000000000001, 1000, 7800, 1.5e-05, 9.9999999999999995e-07, 0.55000000000000004, 0.65000000000000002, 1.2, 1, 8, 2.5, 2, 140, 0.080000000000000002, 0.14999999999999999, 0.080000000000000002, 0.75, 0.69999999999999996, 0.025000000000000001, 0.012, 1, 0.80000000000000004, 12, 12, 0.80000000000000004, 0.41999999999999998, 0.02, 0.02, 0.34999999999999998, 1.1499999999999999, 0.65000000000000002, 60000, 30000, 30, 1.5, 0.5, 0.5, 5, 1000, 0.20000000000000001, 0.84999999999999998, 0.59999999999999998, 0.90000000000000002, 0.90000000000000002, 0.80000000000000004, 0.90000000000000002, 0.5, 1.5, 0.02, 18, 6, 4.5, 0.20000000000000001, 0.34999999999999998, 0.5, 0.25, 0.59999999999999998, 0.02, 0.050000000000000003, 0.80000000000000004, 0.94999999999999996, 1.5, 100000, 6, 0.5, 72, 15, 2, 0.59999999999999998, 0.001, 0.0001, 49.200000000000003, 1270, 2550, 1180, 1, 10000000000, 50000000, 0.00080000000000000004, 0.00040000000000000002, 0.01, 0.080000000000000002, 0.12, 0.10000000000000001, 0.029999999999999999, 0.20000000000000001, 0.23000000000000001, 0.050000000000000003, 1, 1.5, 0.29999999999999999, 10000, 100, 0.02, 0.0050000000000000001, 0.01, 1, 15, 0.59999999999999998, 0.00080000000000000004, 0.040000000000000001, 0.02), (8, 0, 1, 1.6799545689798769, 159.41765306630438, 11.777383486600392, -1.727950631839505, -0.2651598133778279, -9.2399934803060404)); }
analysis printed_ribsRoute { out attribute rows : ScalarValues::Real [*] ordered nonunique = BlueDogMissionSizing::Route((1.0996736993308327, 0.97378372563103299, 1.5624202536526097, 1.5541956985209946), (0.94999999999999996, 0.5, 0.5, 0.5, 1, 100000, 72)); }
}

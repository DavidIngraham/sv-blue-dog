package BlueDogSailTrade {
    doc /* Control architecture and section camber are independent design axes.
     * A cambered wing could also use aerodynamic tail control. These three named
     * configurations are a starting comparison, not mutually exclusive physics. */
    private import ScalarValues::*;
    enum def Evidence { unknown; passed; failed; }
    part def Candidate {
        attribute label : String;
        attribute membraneSail : Boolean;
        attribute aerodynamicTrim : Boolean;
        attribute concept : String;
        attribute durability : String;
        attribute energy : String;
        attribute sailing : String;
        attribute recovery : String;
        attribute manufacturing : String;
        attribute nextEvidence : String;
        // Ordered: wet/survival durability, energy, polar/progress, capsize/control,
        // manufacturing, lifting, voyage reliability. Unknown is never a failure.
        attribute gates : Evidence [7] ordered nonunique default =
            (Evidence::unknown, Evidence::unknown, Evidence::unknown, Evidence::unknown,
             Evidence::unknown, Evidence::unknown, Evidence::unknown);
    }
    part tailWing : Candidate {
        attribute :>> label = "Tail-controlled rigid wing";
        attribute :>> membraneSail = false;
        attribute :>> aerodynamicTrim = true;
        attribute :>> concept = "Freely rotating main wing, provisionally symmetric, with a tail and actuated elevator-like trim tab. Tail/wing aerodynamic moments set incidence; no assumption of a powered whole-wing bearing.";
        attribute :>> durability = "Avoids sailcloth flogging and sheets; retains bearing, tab linkage, tail-boom, skin/joint and wave-impact failure modes. Rigid wings are not automatically storm-proof.";
        attribute :>> energy = "Low trim-energy potential from aerodynamic balance; measure bearing friction, tab hinge moment and failure-state power. No transfer of full-size Saildrone wattage to Blue Dog.";
        attribute :>> sailing = "Test both tacks and low-Reynolds-number main-wing/tail interaction. Tail authority, stall, gust response and faulted-tab loads remain open.";
        attribute :>> recovery = "Include main wing, tail, boom, tab, actuator and any counterweight as separate mass/volume bodies. Check free, jammed and failed trim states plus sealed, flooded and draining states.";
        attribute :>> manufacturing = "Compatible in principle with printed ribs and glass skins; extra bearings, waterproof actuation, alignment and tail clearance need design.";
        attribute :>> nextEvidence = "Low-speed trim bench; unpowered and jammed-tab gust tests; wet-cycle endurance; actual rig mass/CG and compartment geometry.";
        metadata rationale : ModelingMetadata::Rationale { text = "Co-leading development choice based on passive trim and removing cloth/line wear mechanisms, not demonstrated Blue Dog reliability. See sail-trade.md for primary sources and limitations."; }
    }
    part camberedWing : Candidate {
        attribute :>> label = "Fixed-camber rotating-mast wing";
        attribute :>> membraneSail = false;
        attribute :>> aerodynamicTrim = false;
        attribute :>> concept = "Owner-defined fixed-camber CrescentWing with whole-mast rotation for trim. Square-sail/downwind mode and reaching mode; no camber reversal, flap or tail mechanism is assumed. Evaluate a non-backdrivable gearbox for unpowered position holding as an actuator option, not a selected component.";
        attribute :>> durability = "Avoids cloth flogging and camber-changing joints; retains skin, seam, mast-bearing and trim-drive fatigue and wave-impact loads. Verify holding torque and wear under shock, vibration, lubrication and temperature variation; do not assume every worm gearbox self-locks.";
        attribute :>> energy = "Non-backdrivable gearing may eliminate motor holding current, but not controller standby power or trim energy. Compare measured daily move, hold and idle energy against tail control; include starting friction, gearbox efficiency, trim frequency and gust response. A balanced pivot can reduce drive torque.";
        attribute :>> sailing = "Measure full-angle lift, drag and moment on both tacks, including drag-dominated square/downwind and lift-dominated reaching modes and transitions. Do not inherit symmetric linear-wing polars. Inspect edge geometry before assuming leading/trailing-edge interchange.";
        attribute :>> recovery = "Use actual crescent/swept geometry, dry and retained-water CG, sealed volume, trim angle and failed-drive position. A self-locking drive retains the last trim angle on power loss and cannot passively feather without a release mechanism. Assess locked-angle storm/capsize states and any clutch or emergency depower strategy. Manufacturing CAD is not qualified challenge-vessel geometry.";
        attribute :>> manufacturing = "Closest to existing CAD and useful for coupons/prototypes. Fixed section and rotating mast avoid tail/tab/boom parts; bearing, drive and waterproofing details remain to be designed.";
        attribute :>> nextEvidence = "Inspect CAD section and stations; measure both-mode, both-tack polars, trim moments and drive energy, including depower and jam states; compare against MaxiMOOP and Oshen PC13 directly driven wingsail precedent. Bench-test motor-off holding, wet-cycle wear, daily energy and failed-power depower/recovery; include gearbox mass and CG.";
        metadata rationale : ModelingMetadata::Rationale { text = "Owner confirmed fixed camber, whole-mast trim and square/downwind plus reaching modes. Miller et al., An Alternative Wing Sail Concept for Small Autonomous Sailing Craft, DOI 10.1007/978-3-319-72739-4_1, provides analogous square-sail-derived precedent, not Blue Dog qualification. Oshen PC13 provides ocean-service precedent for directly actuated DynaRig wingsails (https://www.microtransat.org/content.php?p=2026_oshen_cstar), not evidence of identical camber or a non-backdrivable gearbox. Retain alongside tail control pending comparable measurements."; }
    }
    part softSail : Candidate {
        attribute :>> label = "Triangular soft sail";
        attribute :>> membraneSail = true;
        attribute :>> aerodynamicTrim = false;
        attribute :>> concept = "Triangular woven-polyester sail on mast and boom with sheet control. Reefing/furling is a design option requiring explicit mechanism, mass and fault analysis; battens and reinforcement are not excluded.";
        attribute :>> durability = "Flogging, flutter, chafe, UV/stitching degradation and sheet wear create unattended-maintenance concerns. Durable cloth, battens and anti-chafe design can mitigate them; no lifetime failure is established.";
        attribute :>> energy = "Sheet/winch energy and holding strategy must be measured; self-locking or balanced arrangements may have low static draw. Do not assume a continuously powered servo.";
        attribute :>> sailing = "Both-tack sailing is conventional in principle; actual reefed and unreefed low-Re polars are needed. Useful benchmark for mass and performance.";
        attribute :>> recovery = "Lower membrane mass and negligible sealed cloth volume can help, but model mast/boom buoyancy, immersion drag, trapped water and sheet snagging separately.";
        attribute :>> manufacturing = "Simple sailmaking and repair, low rig-mass potential; requires sailcloth and rigging rather than printing every component. Hull FDM/glass requirement does not prohibit a soft sail.";
        attribute :>> nextEvidence = "Unattended flogging/chafe/UV exposure and sheet fault tests over declared mission hours; autonomous depower and recovery demonstration.";
        metadata rationale : ModelingMetadata::Rationale { text = "Deprioritized for the long unattended objective by engineering judgment, not rejected against a measured requirement. Still credible for a shorter Gorge test or performance benchmark."; }
    }
    analysis def TradeAssessment {
        subject candidate : Candidate;
        out attribute candidateName : String = candidate.label;
        out attribute gateCount : Integer = SequenceFunctions::size(candidate.gates);
        out attribute knownFailure : Boolean = candidate.gates->ControlFunctions::exists { in gate : Evidence; gate == Evidence::failed };
        out attribute evidenceComplete : Boolean = candidate.gates->ControlFunctions::forAll { in gate : Evidence; gate != Evidence::unknown };
        out attribute qualified : Boolean = gateCount == 7 and candidate.gates->ControlFunctions::forAll { in gate : Evidence; gate == Evidence::passed };
        out attribute requirementVerdict : String = if knownFailure ? "Failed gate" else if qualified ? "Passed declared gates" else "Inconclusive: evidence missing";
        // Explicit development policy, not an inferred failure probability or weighted score.
        return developmentDecision : String = if knownFailure ? "Resolve verified failure before selection" else
            if qualified ? "Eligible for selection; compare validated margins" else
            if not candidate.membraneSail ? "Co-leading development candidate" else
            "Deprioritize for long unattended service; retain prototype benchmark";
        objective assess { require constraint { gateCount == 7 } }
    }
    analysis tailAssessment : TradeAssessment { subject :>> candidate = tailWing; }
    analysis camberAssessment : TradeAssessment { subject :>> candidate = camberedWing; }
    analysis softAssessment : TradeAssessment { subject :>> candidate = softSail; }
    dependency durabilityCriterion from TradeAssessment to BlueDogRequirements::wetMechanicalIntegrity;
    dependency stormWindCriterion from TradeAssessment to BlueDogRequirements::gorgeSurvivalWind;
    dependency stormWaveCriterion from TradeAssessment to BlueDogRequirements::oceanSurvivalWaves;
    dependency energyCriterion from TradeAssessment to BlueDogRequirements::sustainedEnergyFeasibility;
    dependency progressCriterion from TradeAssessment to BlueDogRequirements::legProgress;
    dependency capsizeCriterion from TradeAssessment to BlueDogRequirements::selfRighting;
    dependency controlCriterion from TradeAssessment to BlueDogRequirements::capsizeControlRecovery;
    dependency liftCriterion from TradeAssessment to BlueDogRequirements::liftMass;
    dependency reliabilityCriterion from TradeAssessment to BlueDogRequirements::missionSuccessProbability;
    dependency reliabilityEvidence from TradeAssessment to BlueDogRequirements::reliabilityEvidence;
    dependency architectureScope from Candidate to BlueDog::Architecture::HullAndRig;
    dependency failureReview from TradeAssessment to BlueDogDFMEA::starter::sailJam;

    part def RigBody {
        doc /* Input contract for the next geometry-based capsize model. Boat-fixed
         * x forward, y port, z up; all lengths m, mass kg, volume m3, time s.
         * Geometry must resolve wetted shape at each heel/pitch/trim; these scalar
         * properties alone do not establish a righting curve. */
        attribute component : String;
        attribute dryMassKg : Real;
        attribute dryCG : Real [3] ordered nonunique;
        attribute sealedVolumeM3 : Real;
        attribute sealedVolumeCentroid : Real [3] ordered nonunique;
        attribute floodableVolumeM3 : Real;
        attribute retainedWaterMassKg : Real;
        attribute retainedWaterCG : Real [3] ordered nonunique;
        attribute fillTimeS : Real;
        attribute drainTimeS : Real;
        attribute geometryReference : String;
        attribute geometryEvidenceAccepted : Boolean default false;
    }
    calc def BuoyancyMomentSensitivity {
        in displacedVolumeM3 : Real;
        in signedHorizontalLeverM : Real;
        in waterDensityKgM3 : Real;
        return momentNm : Real;
        waterDensityKgM3 * 9.80665 * displacedVolumeM3 * signedHorizontalLeverM
    }
    analysis buoyancyIllustration {
        doc /* Ten litres fully immersed at +/-1 m horizontal lever in freshwater.
         * This is a sensitivity example, not a candidate volume or predicted GZ. */
        out attribute positiveMomentNm : Real = BuoyancyMomentSensitivity(0.01,1,1000);
        out attribute negativeMomentNm : Real = BuoyancyMomentSensitivity(0.01,-1,1000);
    }
    dependency geometryForRecovery from RigBody to BlueDogRequirements::selfRighting;
}
package BlueDogSailTradeDocuments {
    private import DocumentQueries::*;
    calc def Candidates :> Query { Named(qualifiedName = ("BlueDogSailTrade::tailWing", "BlueDogSailTrade::camberedWing", "BlueDogSailTrade::softSail")) }
    calc def Concepts :> Query { Project(source = Candidates(), columns = (Column(name = "Candidate", path = "label"), Column(name = "Definition", path = "concept"))) }
    calc def Durability :> Query { Project(source = Candidates(), columns = (Column(name = "Candidate", path = "label"), Column(name = "Durability and reliability", path = "durability"), Column(name = "Energy", path = "energy"))) }
    calc def Recovery :> Query { Project(source = Candidates(), columns = (Column(name = "Candidate", path = "label"), Column(name = "Sailing performance", path = "sailing"), Column(name = "Recovery geometry", path = "recovery"))) }
    calc def Manufacturing :> Query { Project(source = Candidates(), columns = (Column(name = "Candidate", path = "label"), Column(name = "Construction", path = "manufacturing"), Column(name = "Next evidence", path = "nextEvidence"))) }
    calc def Results :> Query { Project(source = Named(qualifiedName = ("BlueDogSailTrade::tailAssessment", "BlueDogSailTrade::camberAssessment", "BlueDogSailTrade::softAssessment")), columns = (Column(name = "Candidate", path = "candidateName"), Column(name = "Development decision", path = "developmentDecision"), Column(name = "Requirement verdict", path = "requirementVerdict"))) }
    calc def Traces :> Query { Project(source = WhereType(source = Descendants(source = Named(qualifiedName = "BlueDogSailTrade")), type = "Dependency"), columns = (Column(name = "Analysis element", cell = { in row : KerML::Root::Dependency; row.client }), Column(name = "Requirement / architecture", cell = { in row : KerML::Root::Dependency; row.supplier }))) }
    part def Report :> Document {
        attribute redefines title = "Sail architecture trade study";
        part scope : Paragraph { attribute redefines text = "Preliminary qualitative development selection. All physical requirement gates remain unknown. No numeric reliability rates or arbitrary weighted scores are assigned. Neither rigid concept is mission-qualified; the soft sail is deprioritized, not proven noncompliant. Sources and decision rationale: sail-trade.md."; }
        part decision : Section { attribute redefines title = "Native analysis conclusion"; part rows : Table { calc rows : Results; } }
        part concepts : Section { attribute redefines title = "Candidate definitions"; part rows : Table { calc rows : Concepts; } }
        part durability : Section { attribute redefines title = "Durability and energy"; part rows : Table { calc rows : Durability; } }
        part recovery : Section { attribute redefines title = "Performance and capsize"; part rows : Table { calc rows : Recovery; } }
        part construction : Section { attribute redefines title = "Manufacturing and evidence"; part rows : Table { calc rows : Manufacturing; } }
        part trace : Section { attribute redefines title = "Requirement and architecture links"; part rows : Table { calc rows : Traces; } }
    }
}

package BlueDogDesignResults {
    doc /* Generated by scripts/publish_design_search.py from saved search inputs.
     * Numerical outputs are recomputed by SearchAudit; no physical evidence is accepted. */
    part full_envelope : BlueDogDesignSearch::SearchResult {
        attribute :>> label = "full_envelope";
        attribute :>> design = (2.0213593649870587, 0.2000000000000004, 1.8, 2.2222222222222232, 0.022527339555742515, 0.84999999999999964, 0.016651486239392787, 0.22201981652535857, 9.9552198240271927, -0.074066345846811113, 204.24019570434945, 0.22566455147435771, 0.46814210744077212);
        attribute :>> evidenceAccepted = false;
        part point1 :> points {
            attribute :>> index = 1;
            attribute :>> operatingValues = (1.1956781372524226, 32.049489916687357, 11.601380065146397, 5.1537313736146455, -0.83801626328948231, 13.299319570601824);
        }
        part point2 :> points {
            attribute :>> index = 2;
            attribute :>> operatingValues = (1.1319579010595644, 147.01539342387963, 12, -0.88077153529714991, 0.14244360268201106, -2.1902695009257513);
        }
        part point3 :> points {
            attribute :>> index = 3;
            attribute :>> operatingValues = (1.8432790273004394, 48.851398771030738, 7.3584949424775896, 3.1339333732122796, -0.49402510727429672, 18.136143803240394);
        }
        part point4 :> points {
            attribute :>> index = 4;
            attribute :>> operatingValues = (2.0100069958727089, 126.28581072539416, 9.9659216494540281, -0.14315106844326309, 0.022677123687891765, -1.1274289248679814);
        }
        part point5 :> points {
            attribute :>> index = 5;
            attribute :>> operatingValues = (1.5956695246920523, 49.314723511319343, 1.0350045180345757, 4.5960470772786124, -0.73284630435755105, 19.471220636602943);
        }
        part point6 :> points {
            attribute :>> index = 6;
            attribute :>> operatingValues = (2.4778998239241927, 125.15454027355715, 1.475925379785977, -0.2297439280146012, 0.035587482647123636, -2.7514669855887419);
        }
        part point7 :> points {
            attribute :>> index = 7;
            attribute :>> operatingValues = (1.6300883836305224, 51.142021552006966, 7.5279380176425015, 3.6457311164596451, -0.54600796293350484, 16.942790796359752);
        }
        part point8 :> points {
            attribute :>> index = 8;
            attribute :>> operatingValues = (1.7299325063596993, 133.97500703028058, 10.817377180848206, -0.66608665211583507, 0.10067606620255987, -3.8965549586506718);
        }
    }
    analysis full_envelopeAudit : BlueDogDesignSearch::SearchAudit { subject :>> trial = full_envelope; }
    part nominal_5ms : BlueDogDesignSearch::SearchResult {
        attribute :>> label = "nominal_5ms";
        attribute :>> design = (2.8934183935389211, 0.20000000000000012, 1.3999833407185869, 2.8571768560804185, 0.014887750037073825, 0.84999999999999987, 0.010701223746549592, 0.14268298328735401, 12.999999999999977, -0.035377586969575006, 204.82381899504048, 0.22663344242747133, 0.53151760118758162);
        attribute :>> evidenceAccepted = false;
        part point3 :> points {
            attribute :>> index = 3;
            attribute :>> operatingValues = (1.8904488573259437, 33.156742724935697, 11.355962243643024, 7.7922674060947266, -3.9579933629618864, 19.471220637169104);
        }
        part point4 :> points {
            attribute :>> index = 4;
            attribute :>> operatingValues = (1.7128175806555701, 148.28251812914817, 11.999999999999996, -1.809857245281222, 0.92037037232963215, -4.3247014218956217);
        }
    }
    analysis nominal_5msAudit : BlueDogDesignSearch::SearchAudit { subject :>> trial = nominal_5ms; }
}

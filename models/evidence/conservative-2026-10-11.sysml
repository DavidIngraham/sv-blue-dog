// Generated by tools.boat_analysis.evidence.model; edit source evidence only through a new recorded run.
package BlueDogCurrentSizing {
    private import ScalarValues::*;
    doc /* Exploratory run at source revision bfea3b0dcf95130994ddaf2b8562fb7383ba1bdc.
     * Evidence: evidence/runs/2026-10-11-conservative/manifest.json.
     * Frozen conservative-policy rerun; publishing this projection does not execute a new solve. */
    part candidate : MarineDesign::Design {
        attribute :>> length_m = 2.7444989596416272;
        attribute :>> beam_m = 0.74942251593434195;
        attribute :>> bottom_depth_m = 0.044327803861752196;
        attribute :>> deck_height_m = 0.089625828712692562;
        attribute :>> sail_m2 = 1.515919520175065;
        attribute :>> sail_AR = 4.889910548873651;
        attribute :>> camber_scale = 1.1322960330557514;
        attribute :>> wing_thickness_scale = 1.9999993213972829;
        attribute :>> mast_fraction = 0.52298134029440424;
        attribute :>> mast_x_fraction = -0.02220701537383768;
        attribute :>> keel_m2 = 0.10175467950966061;
        attribute :>> keel_span_m = 0.5573048453208429;
        attribute :>> rudder_m2 = 0.012079320831068887;
        attribute :>> rudder_span_m = 0.13875587935156675;
        attribute :>> rudder_arm_fraction = 0.64999733283754257;
        attribute :>> ballast_kg = 12.175661579607766;
        attribute :>> battery_Wh = 572.7685742741985;
        attribute :>> panel_m2 = 0.22607287268782394;
        attribute :>> wing_torque_Nm = 7.6440177618377536;
        attribute :>> rudder_torque_Nm = 0.063775554131388565;
        attribute :>> hull_glass_kg_m2 = 0.4509253105356551;
        attribute :>> wing_glass_kg_m2 = 0.62723274069557411;
        attribute :>> keel_glass_kg_m2 = 6.2375394370135302;
        attribute :>> rudder_glass_kg_m2 = 1.1391366089266055;
        attribute :>> hull_rib_pitch_m = 0.022358959190431425;
        attribute :>> foil_rib_pitch_m = 0.22081818364927483;
        attribute :>> battery_x_fraction = 0;
        attribute :>> battery_z_fraction = 0.050000003596957242;
        attribute :>> hull_fullness_exponent = 1.9999996512819562;
    }
    part searchAssessment {
        attribute solverStatus : String = "Feasibility phase did not satisfy all screens";
        attribute activeBounds : String = "wing_thickness_scale (upper, 2); battery_z_fraction (lower, 0.05); hull_fullness_exponent (upper, 2)";
        attribute coarseFeasible : Boolean = false;
        attribute massKg : Real = 40.945157345209878;
        attribute maximumResidual : Real = 0.00015447889732875809;
        attribute minimumMargin : Real = -0.00020038205386162765;
        attribute progressReserveMps : Real = 0.0050000000000000001;
        attribute qualified : Boolean = false;
    }
    part searchConstraint0 {
        attribute label : String = "easterly upstream progress (with numerical search reserve)";
        attribute margin : Real = -0.00020038205386162765;
    }
    part searchConstraint1 {
        attribute label : String = "bodyHandlingMargin";
        attribute margin : Real = -5.3792451419232279e-05;
    }
    part searchConstraint2 {
        attribute label : String = "case 5: wingDriveMargin";
        attribute margin : Real = -2.4747622110243839e-05;
    }
    part searchConstraint3 {
        attribute label : String = "keelHandlingMargin";
        attribute margin : Real = -1.3662940273828639e-05;
    }
    part searchConstraint4 {
        attribute label : String = "panelDeflectionMargin";
        attribute margin : Real = -2.3130333082210797e-06;
    }
    part searchConstraint5 {
        attribute label : String = "case 5: cycleMargin";
        attribute margin : Real = -1.3690875391601451e-06;
    }
    part searchConstraint6 {
        attribute label : String = "case 0: delftDomain6 (search reserve)";
        attribute margin : Real = -5.5511151231257827e-17;
    }
    part searchConstraint7 {
        attribute label : String = "case 1: delftDomain6 (search reserve)";
        attribute margin : Real = -5.5511151231257827e-17;
    }
    part searchConstraint8 {
        attribute label : String = "case 2: delftDomain6 (search reserve)";
        attribute margin : Real = -5.5511151231257827e-17;
    }
    part searchConstraint9 {
        attribute label : String = "case 3: delftDomain6 (search reserve)";
        attribute margin : Real = -5.5511151231257827e-17;
    }
    part searchConstraint10 {
        attribute label : String = "case 4: delftDomain6 (search reserve)";
        attribute margin : Real = -5.5511151231257827e-17;
    }
    part searchConstraint11 {
        attribute label : String = "case 5: delftDomain6 (search reserve)";
        attribute margin : Real = -5.5511151231257827e-17;
    }
    part convergence0 {
        attribute label : String = "forward, beta 0, wake";
        attribute passesScreen : Boolean = true;
        attribute CLtot : Real = 0.0010974820100000393;
        attribute CDi : Real = 0.00084670703500000499;
        attribute CMytot : Real = 0.00020432221599998857;
    }
    part convergence1 {
        attribute label : String = "forward, beta 0, mesh";
        attribute passesScreen : Boolean = true;
        attribute CLtot : Real = 0.017708813035000048;
        attribute CDi : Real = 0.0064258317499999995;
        attribute CMytot : Real = 0.0031552284759999993;
    }
    part convergence2 {
        attribute label : String = "reverse, beta 0, wake";
        attribute passesScreen : Boolean = true;
        attribute CLtot : Real = 0.001327419566000021;
        attribute CDi : Real = 0.00085670971500000082;
        attribute CMytot : Real = 0.00024245977799999818;
    }
    part convergence3 {
        attribute label : String = "reverse, beta 0, mesh";
        attribute passesScreen : Boolean = true;
        attribute CLtot : Real = 0.020571112351000065;
        attribute CDi : Real = 0.0053078105269999953;
        attribute CMytot : Real = 0.0033816664710000222;
    }
    part convergence4 {
        attribute label : String = "forward, beta 20, wake";
        attribute passesScreen : Boolean = true;
        attribute CLtot : Real = 0.0030444152249999856;
        attribute CDi : Real = 0.00093538887700000961;
        attribute CMytot : Real = 0.00074289939299999885;
    }
    part convergence5 {
        attribute label : String = "forward, beta 20, mesh";
        attribute passesScreen : Boolean = true;
        attribute CLtot : Real = 0.015921558743000053;
        attribute CDi : Real = 0.0030920898859999879;
        attribute CMytot : Real = 0.0028109218799999974;
    }
    part coarseGrid0 {
        attribute label : String = "forward, beta 0: mesh 24/wake 5 to mesh 72/wake 30";
        attribute CLtot : Real = 0.050497159055000074;
        attribute CDi : Real = 0.007092610272000005;
        attribute CMytot : Real = 0.0098591795550000139;
    }
    part coarseGrid1 {
        attribute label : String = "reverse, beta 0: mesh 24/wake 5 to mesh 72/wake 30";
        attribute CLtot : Real = 0.065062912521000049;
        attribute CDi : Real = 0.0035108145999999951;
        attribute CMytot : Real = 0.011013893448000023;
    }
    part coarseGrid2 {
        attribute label : String = "forward, beta 20: mesh 24/wake 5 to mesh 72/wake 30";
        attribute CLtot : Real = 0.048231737603000036;
        attribute CDi : Real = 0.0029270257569999902;
        attribute CMytot : Real = 0.0088007662020000016;
    }
    dependency assumptions from candidate to BlueDogAerodynamicPolicy::sizing;
    dependency convergenceBasis from convergence0 to BlueDogAerodynamicPolicy::convergenceInputs;
    part ingress0 {
        attribute label : String = "sealed, water 1000 kg/m3";
        attribute minimumRestoringNm : Real = 1.0494144734863899;
        attribute missingPitchRoots : Integer = 0;
        attribute unstablePitchSamples : Integer = 80;
        attribute retainedWaterKg : Real = 0;
    }
    dependency ingressBasis0 from ingress0 to BlueDogRequirements::selfRighting;
    part ingress1 {
        attribute label : String = "free_flooding_homogenized, water 1000 kg/m3";
        attribute minimumRestoringNm : Real = -50.2386312599711;
        attribute missingPitchRoots : Integer = 0;
        attribute unstablePitchSamples : Integer = 0;
        attribute retainedWaterKg : Real = 0;
    }
    dependency ingressBasis1 from ingress1 to BlueDogRequirements::selfRighting;
    part ingress2 {
        attribute label : String = "full_water_retention, water 1000 kg/m3";
        attribute minimumRestoringNm : Real = -1196.3826506441972;
        attribute missingPitchRoots : Integer = 0;
        attribute unstablePitchSamples : Integer = 73;
        attribute retainedWaterKg : Real = 90.175153011111306;
    }
    dependency ingressBasis2 from ingress2 to BlueDogRequirements::selfRighting;
    part ingress3 {
        attribute label : String = "sealed, water 1025 kg/m3";
        attribute minimumRestoringNm : Real = 1.0760870573636374;
        attribute missingPitchRoots : Integer = 0;
        attribute unstablePitchSamples : Integer = 80;
        attribute retainedWaterKg : Real = 0;
    }
    dependency ingressBasis3 from ingress3 to BlueDogRequirements::selfRighting;
    part ingress4 {
        attribute label : String = "free_flooding_homogenized, water 1025 kg/m3";
        attribute minimumRestoringNm : Real = -50.328307543483042;
        attribute missingPitchRoots : Integer = 0;
        attribute unstablePitchSamples : Integer = 0;
        attribute retainedWaterKg : Real = 0;
    }
    dependency ingressBasis4 from ingress4 to BlueDogRequirements::selfRighting;
    part ingress5 {
        attribute label : String = "full_water_retention, water 1025 kg/m3";
        attribute minimumRestoringNm : Real = -1228.6340739385746;
        attribute missingPitchRoots : Integer = 0;
        attribute unstablePitchSamples : Integer = 73;
        attribute retainedWaterKg : Real = 92.429531836389089;
    }
    dependency ingressBasis5 from ingress5 to BlueDogRequirements::selfRighting;
    part nominal : BlueDogSizingEvidence::Scenario {
        attribute :>> label = "conservative primary";
        attribute limitingScreens : String = "bodyHandlingMargin: -0.001021; keelHandlingMargin: -1.366e-05; panelDeflectionMargin: -2.313e-06";
        attribute easterlyDownstreamMps : Real = 2.3056125826917206;
        attribute easterlyUpstreamMps : Real = 0.50363121135764954;
        attribute easterlyTimeLabel : String = if easterlyDownstreamMps <= 0 or easterlyUpstreamMps <= 0 ? "No completion (duration penalty)" else "67.2";
        attribute westerlyDownstreamMps : Real = 2.0036312113576495;
        attribute westerlyUpstreamMps : Real = 0.80561258269172065;
        attribute westerlyTimeLabel : String = if westerlyDownstreamMps <= 0 or westerlyUpstreamMps <= 0 ? "No completion (duration penalty)" else "48.34";
        attribute :>> numericallyBalanced = true;
        attribute :>> missingPitchRoots = 0;
        attribute :>> pitchUnstableSamples = 80;
        attribute :>> diagnosticControlCases = 0;
        attribute :>> easterlyHours = 67.202891425471918;
        attribute :>> westerlyHours = 48.344035523497915;
        attribute :>> massKg = 40.959664207244543;
        attribute :>> evidenceAccepted = false;
        attribute :>> operatingMargins = (-1.0738077094174514e-12);
        attribute :>> structuralMargins = (0.87981970636864471,0.72533327476282428,0.76414018267156358,0.5482778478124154,0.53081816867579734,1.5094254794956186e-06,0.00010888679536580348,1.9251827980681924e-06,0.75999962991481329,-2.3130333082210797e-06,-0.0010209165870636028,0.54313723917493884,-1.3662940273828639e-05,0.72725305986942934,0.79646331455221597,0.95950074549785347,0.41519734353939503,2.6333229830643909,0.95757954217234753,0.9556510022361272,0.00030807993062609285,0.51838112751959642);
        attribute :>> routeMargins = (3.6112251653834413,0.0072624227152990883,0.066626507979556715,3.0072624227152991,0.61122516538344129,0.32855506217364006);
        attribute :>> restoringMomentsNm = (1.049842271115051,13.012491198374299,1.0494144734863899,13.041343034437229);
    }
    analysis nominalReview : BlueDogSizingEvidence::Review { subject :>> scenario = nominal; }
    part construction : BlueDogSizingEvidence::Scenario {
        attribute :>> label = "construction";
        attribute limitingScreens : String = "keelDeflectionMargin: -0.4126; rudderDeflectionMargin: -0.3174; wingDeflectionMargin: -0.2601";
        attribute easterlyDownstreamMps : Real = 2.2906021862251631;
        attribute easterlyUpstreamMps : Real = 0.48600195233620691;
        attribute easterlyTimeLabel : String = if easterlyDownstreamMps <= 0 or easterlyUpstreamMps <= 0 ? "No completion (duration penalty)" else "69.28";
        attribute westerlyDownstreamMps : Real = 1.9860019523362069;
        attribute westerlyUpstreamMps : Real = 0.79060218622516309;
        attribute westerlyTimeLabel : String = if westerlyDownstreamMps <= 0 or westerlyUpstreamMps <= 0 ? "No completion (duration penalty)" else "49.12";
        attribute :>> numericallyBalanced = true;
        attribute :>> missingPitchRoots = 0;
        attribute :>> pitchUnstableSamples = 80;
        attribute :>> diagnosticControlCases = 0;
        attribute :>> easterlyHours = 69.282536797794165;
        attribute :>> westerlyHours = 49.121744724102008;
        attribute :>> massKg = 43.768205422754356;
        attribute :>> evidenceAccepted = false;
        attribute :>> operatingMargins = (-2.2204460492503131e-16);
        attribute :>> structuralMargins = (0.838404277233054,0.65393374797458981,0.66677857355458703,0.40488973760098979,0.36910954033680954,-0.26014871654530691,-0.41264055406342282,-0.31742291986566529,0.73466177362319174,0.02740531892342124,-0.095324405591018735,0.51357357854175012,-0.01792477098202272,0.68179523651433427,0.75539474536477358,0.83376247150657323,0.41348615315658499,2.6333229830643909,0.95601675519677598,0.95197412765904066,-0.12918473013333176,0.46745176722933535);
        attribute :>> routeMargins = (3.5812043724503262,-0.027996095327586179,0.037742544475081075,2.9720039046724138,0.58120437245032619,0.31775354549858326);
        attribute :>> restoringMomentsNm = (-3.2193083517886256,9.3607052803174291,-3.2198832690518038,9.3853882989971336);
    }
    analysis constructionReview : BlueDogSizingEvidence::Review { subject :>> scenario = construction; }
    part aerodynamic : BlueDogSizingEvidence::Scenario {
        attribute :>> label = "aerodynamic";
        attribute limitingScreens : String = "easterly duration: -0.8456; easterly upstream progress: -0.5393; bodyHandlingMargin: -0.001021";
        attribute easterlyDownstreamMps : Real = 2.2600639013287775;
        attribute easterlyUpstreamMps : Real = 0.2303460675486747;
        attribute easterlyTimeLabel : String = if easterlyDownstreamMps <= 0 or easterlyUpstreamMps <= 0 ? "No completion (duration penalty)" else "132.9";
        attribute westerlyDownstreamMps : Real = 1.7303460675486746;
        attribute westerlyUpstreamMps : Real = 0.76006390132877732;
        attribute westerlyTimeLabel : String = if westerlyDownstreamMps <= 0 or westerlyUpstreamMps <= 0 ? "No completion (duration penalty)" else "52.6";
        attribute :>> numericallyBalanced = true;
        attribute :>> missingPitchRoots = 0;
        attribute :>> pitchUnstableSamples = 80;
        attribute :>> diagnosticControlCases = 0;
        attribute :>> easterlyHours = 132.88220447802564;
        attribute :>> westerlyHours = 52.599942394214558;
        attribute :>> massKg = 40.959664207244543;
        attribute :>> evidenceAccepted = false;
        attribute :>> operatingMargins = (5.5511151231257827e-16);
        attribute :>> structuralMargins = (0.87981970636864471,0.72533327476282428,0.76414018267156358,0.5482778478124154,0.53081816867579734,1.5094254794956186e-06,0.00010888679536580348,1.9251827980681924e-06,0.75999962991481329,-2.3130333082210797e-06,-0.0010209165870636028,0.54313723917493884,-1.3662940273828639e-05,0.72725305986942934,0.79646331455221597,0.95950074549785347,0.41519734353939503,2.6333229830643909,0.95757954217234753,0.9556510022361272,0.00030807993062609285,0.51838112751959642);
        attribute :>> routeMargins = (3.5201278026575551,-0.53930786490265059,-0.84558617330591179,2.4606921350973492,0.52012780265755465,0.26944524452479779);
        attribute :>> restoringMomentsNm = (1.049842271115051,13.012491198374299,1.0494144734863899,13.041343034437229);
    }
    analysis aerodynamicReview : BlueDogSizingEvidence::Review { subject :>> scenario = aerodynamic; }
    part hydrodynamic : BlueDogSizingEvidence::Scenario {
        attribute :>> label = "hydrodynamic";
        attribute limitingScreens : String = "easterly upstream progress: -0.05018; bodyHandlingMargin: -0.001021; keelHandlingMargin: -1.366e-05";
        attribute easterlyDownstreamMps : Real = 2.2738890506140939;
        attribute easterlyUpstreamMps : Real = 0.47491012249263043;
        attribute easterlyTimeLabel : String = if easterlyDownstreamMps <= 0 or easterlyUpstreamMps <= 0 ? "No completion (duration penalty)" else "70.71";
        attribute westerlyDownstreamMps : Real = 1.9749101224926304;
        attribute westerlyUpstreamMps : Real = 0.77388905061409363;
        attribute westerlyTimeLabel : String = if westerlyDownstreamMps <= 0 or westerlyUpstreamMps <= 0 ? "No completion (duration penalty)" else "49.96";
        attribute :>> numericallyBalanced = true;
        attribute :>> missingPitchRoots = 0;
        attribute :>> pitchUnstableSamples = 80;
        attribute :>> diagnosticControlCases = 0;
        attribute :>> easterlyHours = 70.706577140657231;
        attribute :>> westerlyHours = 49.959084674485325;
        attribute :>> massKg = 40.959664207244543;
        attribute :>> evidenceAccepted = false;
        attribute :>> operatingMargins = (-1.5787371410169726e-13);
        attribute :>> structuralMargins = (0.87981970636864471,0.72533327476282428,0.76414018267156358,0.5482778478124154,0.53081816867579734,1.5094254794956186e-06,0.00010888679536580348,1.9251827980681924e-06,0.75999962991481329,-2.3130333082210797e-06,-0.0010209165870636028,0.54313723917493884,-1.3662940273828639e-05,0.72725305986942934,0.79646331455221597,0.95950074549785347,0.41519734353939503,2.6333229830643909,0.95757954217234753,0.9556510022361272,0.00030807993062609285,0.51838112751959642);
        attribute :>> routeMargins = (3.5477781012281877,-0.050179755014739147,0.017964206379760705,2.9498202449852609,0.54777810122818726,0.30612382396548155);
        attribute :>> restoringMomentsNm = (1.049842271115051,13.012491198374299,1.0494144734863899,13.041343034437229);
    }
    analysis hydrodynamicReview : BlueDogSizingEvidence::Review { subject :>> scenario = hydrodynamic; }
    part energy : BlueDogSizingEvidence::Scenario {
        attribute :>> label = "energy";
        attribute limitingScreens : String = "operating/energy: -0.6651; bodyHandlingMargin: -0.001021; keelHandlingMargin: -1.366e-05";
        attribute easterlyDownstreamMps : Real = 2.3056125826917206;
        attribute easterlyUpstreamMps : Real = 0.50363088148527724;
        attribute easterlyTimeLabel : String = if easterlyDownstreamMps <= 0 or easterlyUpstreamMps <= 0 ? "No completion (duration penalty)" else "67.2";
        attribute westerlyDownstreamMps : Real = 2.003630881485277;
        attribute westerlyUpstreamMps : Real = 0.80561258269172065;
        attribute westerlyTimeLabel : String = if westerlyDownstreamMps <= 0 or westerlyUpstreamMps <= 0 ? "No completion (duration penalty)" else "48.34";
        attribute :>> numericallyBalanced = true;
        attribute :>> missingPitchRoots = 0;
        attribute :>> pitchUnstableSamples = 80;
        attribute :>> diagnosticControlCases = 8;
        attribute :>> easterlyHours = 67.202927551353511;
        attribute :>> westerlyHours = 48.344037805982943;
        attribute :>> massKg = 40.959664207244543;
        attribute :>> evidenceAccepted = false;
        attribute :>> operatingMargins = (-0.66514228651272789);
        attribute :>> structuralMargins = (0.87981970636864471,0.72533327476282428,0.76414018267156358,0.5482778478124154,0.53081816867579734,1.5094254794956186e-06,0.00010888679536580348,1.9251827980681924e-06,0.75999962991481329,-2.3130333082210797e-06,-0.0010209165870636028,0.54313723917493884,-1.3662940273828639e-05,0.72725305986942934,0.79646331455221597,0.95950074549785347,0.41519734353939503,2.6333229830643909,0.95757954217234753,0.9556510022361272,0.00030807993062609285,0.51838112751959642);
        attribute :>> routeMargins = (3.6112251653834413,0.0072617629705544751,0.066626006231201185,3.007261762970554,0.61122516538344129,0.32855503047245915);
        attribute :>> restoringMomentsNm = (1.049842271115051,13.012491198374299,1.0494144734863899,13.041343034437229);
    }
    analysis energyReview : BlueDogSizingEvidence::Review { subject :>> scenario = energy; }
    part combined : BlueDogSizingEvidence::Scenario {
        attribute :>> label = "combined";
        attribute limitingScreens : String = "easterly duration: -1.389e+04; easterly upstream progress: -1.358; operating/energy: -0.6649";
        attribute easterlyDownstreamMps : Real = 2.355963735424865;
        attribute easterlyUpstreamMps : Real = -0.17914757843473827;
        attribute easterlyTimeLabel : String = if easterlyDownstreamMps <= 0 or easterlyUpstreamMps <= 0 ? "No completion (duration penalty)" else "1e+06";
        attribute westerlyDownstreamMps : Real = 1.8208524215652617;
        attribute westerlyUpstreamMps : Real = 0.35596373542486504;
        attribute westerlyTimeLabel : String = if westerlyDownstreamMps <= 0 or westerlyUpstreamMps <= 0 ? "No completion (duration penalty)" else "93.29";
        attribute :>> numericallyBalanced = true;
        attribute :>> missingPitchRoots = 0;
        attribute :>> pitchUnstableSamples = 80;
        attribute :>> diagnosticControlCases = 8;
        attribute :>> easterlyHours = 1000000;
        attribute :>> westerlyHours = 93.290785088646743;
        attribute :>> massKg = 43.768205422754356;
        attribute :>> evidenceAccepted = false;
        attribute :>> operatingMargins = (-0.66487531565994251);
        attribute :>> structuralMargins = (0.838404277233054,0.65393374797458981,0.66677857355458703,0.40488973760098979,0.36910954033680954,-0.26014871654530691,-0.41264055406342282,-0.31742291986566529,0.73466177362319174,0.02740531892342124,-0.095324405591018735,0.51357357854175012,-0.01792477098202272,0.68179523651433427,0.75539474536477358,0.83376247150657323,0.41348615315658499,2.6333229830643909,0.95601675519677598,0.95197412765904066,-0.12918473013333176,0.46745176722933535);
        attribute :>> routeMargins = (3.7119274708497301,-1.3582951568694765,-13887.888888888889,2.6417048431305235,-0.28807252915026993,-0.29570534845342689);
        attribute :>> restoringMomentsNm = (-3.2193083517886256,9.3607052803174291,-3.2198832690518038,9.3853882989971336);
    }
    analysis combinedReview : BlueDogSizingEvidence::Review { subject :>> scenario = combined; }
    dependency candidateBasis from candidate to BlueDogDesignDecisions::sizingBaseline;
}

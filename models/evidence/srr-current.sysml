// Generated by tools.publishing.srr from immutable run evidence.
package BlueDogSRRCurrent {
    private import ScalarValues::*;
    attribute evidenceManifest : String = "evidence/runs/2026-10-13-srr-readiness/manifest.json";
    part candidate {
        attribute batteryWh : Real = 440.0;
        attribute hullBeamM : Real = 0.26;
        attribute massKg : Real = 10.312830010265998;
        attribute westerlyPassageHours : Real = 33.86883519742054;
        attribute departureWh : Real = 316.8;
        attribute requiredWh : Real = 312.82633955094434;
        attribute energyHeadroomWh : Real = 3.9736604490556715;
        attribute balanced : Boolean = true;
        attribute staticScreensPass : Boolean = true;
        attribute physicallyQualified : Boolean = false;
        doc /* Retained concept with revised battery capacity and hull beam; nominal refined static replay.
         * Not a new optimum, hardware selection, dynamic recovery proof or mission qualification. */
    }
    dependency energyBasis from candidate to BlueDogConceptCredibility::passagePolicy;
    dependency recoveryBasis from candidate to BlueDogRequirements::lowEnergyRecovery;
}

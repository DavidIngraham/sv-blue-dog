// Generated by tools.boat_analysis.evidence.continuation.
package BlueDogSizingContinuation {
    private import ScalarValues::*;
    doc /* Coarse fixed-length feasibility only; no refined replay or physical qualification.
     * Hull length does not bound the full vessel footprint. Appendage geometry/model applicability,
     * chronological voyage energy and free-pitch dynamic recovery require further assessment. */
    part summary {
        attribute targetM : Real = 1.2;
        attribute smallestFeasibleM : Real = 1.2;
        attribute targetReached : Boolean = true;
        attribute qualified : Boolean = false;
    }
    part stage0 {
        attribute lengthM : Real = 2.0;
        attribute feasible : Boolean = true;
        attribute maximumResidual : Real = 7.145127156604758e-10;
        attribute minimumMargin : Real = -6.144964537213582e-10;
    }
    part stage1 {
        attribute lengthM : Real = 1.8;
        attribute feasible : Boolean = true;
        attribute maximumResidual : Real = 1.7880595226671403e-09;
        attribute minimumMargin : Real = -2.4811729580631603e-10;
    }
    part stage2 {
        attribute lengthM : Real = 1.6;
        attribute feasible : Boolean = true;
        attribute maximumResidual : Real = 4.353140070634254e-11;
        attribute minimumMargin : Real = -1.2223466683281003e-10;
    }
    part stage3 {
        attribute lengthM : Real = 1.4;
        attribute feasible : Boolean = true;
        attribute maximumResidual : Real = 2.0398403360033512e-05;
        attribute minimumMargin : Real = -1.2719669004734868e-06;
    }
    part stage4 {
        attribute lengthM : Real = 1.2;
        attribute feasible : Boolean = true;
        attribute maximumResidual : Real = 5.669689494665064e-05;
        attribute minimumMargin : Real = -4.6576547404919566e-05;
    }
    part candidate : MarineDesign::Design {
        attribute :>> length_m = 1.2;
        attribute :>> beam_m = 0.4344000000003233;
        attribute :>> bottom_depth_m = 0.04036604075998614;
        attribute :>> deck_height_m = 0.09446793532039352;
        attribute :>> sail_m2 = 0.8143812403943567;
        attribute :>> sail_AR = 2.0911634829244634;
        attribute :>> camber_scale = 1.1746000320485857;
        attribute :>> wing_thickness_scale = 1.1354616735897594;
        attribute :>> mast_fraction = 0.5120755733321997;
        attribute :>> mast_x_fraction = 0.029996841913039862;
        attribute :>> keel_m2 = 0.09591195537596085;
        attribute :>> keel_span_m = 0.5482450099155232;
        attribute :>> rudder_m2 = 0.09205295658604393;
        attribute :>> rudder_span_m = 0.08;
        attribute :>> rudder_arm_fraction = 0.5164052616843922;
        attribute :>> ballast_kg = 9.627177799148448;
        attribute :>> battery_Wh = 50.0;
        attribute :>> panel_m2 = 0.12068262127207481;
        attribute :>> wing_torque_Nm = 2.64136023561948;
        attribute :>> rudder_torque_Nm = 2.2438440735092002;
        attribute :>> hull_glass_kg_m2 = 0.4733356434802783;
        attribute :>> wing_glass_kg_m2 = 0.20000000000000012;
        attribute :>> keel_glass_kg_m2 = 4.067487321205885;
        attribute :>> rudder_glass_kg_m2 = 0.23249038742721195;
        attribute :>> hull_rib_pitch_m = 0.023470086332562604;
        attribute :>> foil_rib_pitch_m = 0.09251996467631225;
        attribute :>> battery_x_fraction = -0.3464999999999999;
        attribute :>> battery_z_fraction = 0.09533437422856002;
        attribute :>> hull_fullness_exponent = 1.5466427151983588;
    }
    dependency basis from candidate to BlueDogDesignDecisions::sizingBaseline;
    part assessment {
        attribute massKg : Real = 22.257347572176332;
        attribute westerlyHours : Real = 23.97409327486867;
        attribute rudderChordM : Real = candidate.rudder_m2 / candidate.rudder_span_m;
        attribute rudderAspectRatio : Real = candidate.rudder_span_m * candidate.rudder_span_m / candidate.rudder_m2;
        attribute qualified : Boolean = false;
    }
}
